# -*- coding: utf-8 -*-
"""FreeCAD Lay Flat for CNC 0.12.11 -- FreeCAD macro, millimetres. Requires lay_flat_sheet.py.

Run in FreeCAD. Select finished Bodies/parts (optional); otherwise the dialog
lists Bodies. Each solid is one part. Source objects are never changed.
Manual solid-part selection. Panel tags are defaults, never exclusion rules.
Thickness is measured from selected geometry; there is no stock-thickness whitelist.
Supported: planar pockets, perpendicular holes/drill tips, ruled tapered cuts,
and convex edge roundovers. Tapers carry explicit angle/depth contours; rounded
finishing is marked as reference regions. Export solids accompany every export.
Optional native fillet removal affects export copies only, with a selectable radius.
Prismatic/taper geometry is reconstructed; residual removal must stay inside
identified roundover envelopes. Rebate extensions cannot remove final material.
Fixed rotations/grain controls and stock sheets are set in the export dialog.
"""
import csv
import itertools
import json
import math
import os
import re
import tempfile
import traceback
from datetime import datetime
from pathlib import Path

import FreeCAD as App
import Part

VERSION = '0.12.11'
PANEL_TAG = 'LayFlatPanel'
STOCK_THICKNESS_TOL = 0.05
TOL = 1e-5
ANG_TOL = 1e-7
TAPER_ANGLE_TOL_DEG = 1e-4  # taper faces whose angles agree this closely are one cut
EXACT_FIT_TOL = 1e-6  # spline edges this close to a line or arc are rebuilt as one
PANEL_EDGE_CONTINUE_MIN = 1e-3  # mm; nearer a panel edge, taper arcs keep the plain loft (continue_past_panel_edge)
Z = App.Vector(0, 0, 1)


class ExportError(Exception):
    """Geometry or output that cannot be exported without guessing."""


def sheet_runtime():
    """Load the installed companion that restores saved right-click menus."""
    import sys
    folder = Path(globals().get('__file__', App.getUserMacroDir(True))).resolve()
    if folder.is_file():folder = folder.parent
    if str(folder) not in sys.path:sys.path.insert(0, str(folder))
    try:
        import lay_flat_sheet
    except ImportError as exc:
        raise ExportError('The sheet export companion is missing. Install the complete Lay Flat package, including lay_flat_sheet.py.') from exc
    return lay_flat_sheet


def mm(value):
    return ('%.6f' % float(value)).rstrip('0').rstrip('.') or '0'


def token(value):
    # + 0.0 turns -0.0 into 0.0, so a depth of -0.00000001 never becomes an M0 layer.
    return mm(round(value, 4) + 0.0).replace('.', 'P').replace('-', 'M')


def safe_name(value):
    return re.sub(r'[^A-Za-z0-9_-]+', '_', value).strip('_')[:90] or 'Part'


def flat_face(face):
    result = face.copy()
    result.translate(App.Vector(0, 0, -result.CenterOfMass.z))
    if result.normalAt(0, 0).z < 0:
        result.reverse()
    return result


def face_of_wire(wire):
    result = Part.Face(wire)
    if result.normalAt(0, 0).z < 0:
        result.reverse()
    return result


def is_horizontal(face):
    return isinstance(face.Surface, Part.Plane) and abs(face.normalAt(0, 0).z) > 1 - ANG_TOL


def circle_of_wire(wire):
    edges = [e for e in wire.Edges if e.Length > TOL]
    if not edges or not wire.isClosed() or not all(isinstance(e.Curve, Part.Circle) for e in edges):
        return None
    circle = edges[0].Curve
    if any((e.Curve.Center - circle.Center).Length > TOL or abs(e.Curve.Radius - circle.Radius) > TOL for e in edges):
        return None
    if abs(sum(e.Length for e in edges) - 2 * math.pi * circle.Radius) > TOL:
        return None
    return circle.Center, circle.Radius


def validate_edges(wire):
    if not wire.isClosed():
        raise ExportError('An operation boundary is open.')
    if wire.BoundBox.ZLength > TOL:
        raise ExportError('An operation boundary is not planar after flattening.')
    for edge in wire.Edges:
        if edge.Length <= TOL:
            continue
        if not isinstance(edge.Curve, (Part.Line, Part.Circle)):
            raise ExportError('Unsupported %s boundary; only exact lines and circular arcs are exported.' % type(edge.Curve).__name__)


def flatten_solid(solid, normal=None):
    """Rigidly rotate each solid; never flatten the thickness or scale geometry."""
    if not solid.isValid() or solid.Volume <= 0:
        raise ExportError('Part is not a valid positive-volume solid.')
    candidates = []
    if normal is not None:
        candidates = [App.Vector(normal)]
    else:
        for face in sorted(solid.Faces, key=lambda f: -f.Area):
            if isinstance(face.Surface, Part.Plane):
                n = face.normalAt(0, 0)
                if not any(abs(n.dot(c)) > 1 - ANG_TOL for c in candidates):
                    candidates.append(n)
    if not candidates:
        raise ExportError('No planar board face was found.')
    variants = []
    for n in candidates:
        copy = solid.copy()
        copy.Placement = App.Placement(App.Vector(), App.Rotation(n, Z)).multiply(copy.Placement)
        variants.append((copy.optimalBoundingBox().ZLength, copy))
    thickness, copy = min(variants, key=lambda item: item[0])
    if thickness <= TOL:
        raise ExportError('Part has zero thickness.')
    # Resolve the automatic face sign towards the side with more recessed area.
    if normal is None:
        bb = copy.optimalBoundingBox()
        scores = {1: 0.0, -1: 0.0}
        for face in copy.Faces:
            if is_horizontal(face) and bb.ZMin + TOL < face.CenterOfMass.z < bb.ZMax - TOL:
                scores[1 if face.normalAt(0, 0).z > 0 else -1] += face.Area
        if scores[-1] > scores[1] + TOL:
            copy.rotate(App.Vector(), App.Vector(0, 1, 0), 180)
    # Align the longest horizontal straight edge with X, for readable drawings.
    lines = [e for e in copy.Edges if e.Length > TOL and isinstance(e.Curve, Part.Line)
             and e.BoundBox.ZLength < TOL]
    if lines:
        e = max(lines, key=lambda e: e.Length)
        direction = e.valueAt(e.LastParameter) - e.valueAt(e.FirstParameter)
        angle = math.degrees(math.atan2(direction.y, direction.x)) % 180
        copy.rotate(App.Vector(), Z, -angle)
    bb = copy.optimalBoundingBox()
    copy.translate(App.Vector(-bb.XMin, -bb.YMin, -bb.ZMin))
    if normal is None and bb.ZLength >= min(bb.XLength, bb.YLength) - TOL:
        raise ExportError('Ambiguous board thickness. Select a broad planar face and run again.')
    return copy


def operation(kind, side, face, depth=None, diameter=None, tip_depth=None):
    flat = flat_face(face)
    if any(e.Length > TOL and not isinstance(e.Curve, (Part.Line, Part.Circle)) for e in flat.Edges):
        # Spline edges that are exact lines or arcs (a chamfer written as
        # B-splines) are rebuilt as such; anything else fails validate_edges.
        try:
            wires = [Part.Wire([canonical_edge(e) for e in w.OrderedEdges]) for w in flat.Wires]
            rebuilt = Part.makeFace(wires, 'Part::FaceMakerBullseye').Faces
        except (Part.OCCError, ValueError) as exc:
            raise ExportError('An operation boundary could not be rebuilt from exact lines and arcs.') from exc
        if len(rebuilt) != 1:
            raise ExportError('An operation boundary could not be rebuilt from exact lines and arcs.')
        flat = flat_face(rebuilt[0])
    for wire in flat.Wires:
        validate_edges(wire)
    if kind == 'OUTLINE':
        layer = 'OUTLINE_THROUGH'
    elif kind == 'CUTOUT':
        layer = 'CUTOUT_THROUGH'
    elif kind == 'HOLE':
        layer = 'HOLE_D%s_%s' % (token(diameter), 'THROUGH' if depth is None else 'DEPTH_%sMM' % token(depth))
        if tip_depth is not None:
            layer += '_TIP_%sMM' % token(tip_depth)
    else:
        layer = 'POCKET_%sMM' % token(depth)
    return {'kind': kind, 'side': side, 'layer': layer, 'depth_mm': depth,
            'diameter_mm': diameter, 'tip_depth_mm': tip_depth, 'face': flat}


def tapered_cone(face):
    if not isinstance(face.Surface, Part.Cone) or abs(face.Surface.Axis.z) < 1 - ANG_TOL:
        return False
    circles = [e.Curve for e in face.Edges if isinstance(e.Curve, Part.Circle) and e.Length > TOL]
    return len({(round(c.Radius, 6), round(c.Center.z, 6)) for c in circles}) >= 2


def orient_pull_front(shape):
    # A tapered pull gets FRONT on the small-opening side. This changes only
    # the rigid orientation; it does not infer a tool direction from a label.
    votes = []
    for face in shape.Faces:
        if tapered_cone(face):
            circles = [e.Curve for e in face.Edges if isinstance(e.Curve, Part.Circle)]
            small, large = min(circles, key=lambda c: c.Radius), max(circles, key=lambda c: c.Radius)
            if abs(small.Center.z-large.Center.z) > TOL:
                votes.append(small.Center.z > large.Center.z)
    if votes and any(v != votes[0] for v in votes):
        raise ExportError('Opposing tapered features need an explicit machining setup.')
    if votes and not votes[0]:
        shape = shape.copy(); shape.rotate(App.Vector(), App.Vector(1, 0, 0), 180)
        b = shape.optimalBoundingBox(); shape.translate(App.Vector(-b.XMin, -b.YMin, -b.ZMin))
    return shape


def exterior_round(face, thickness):
    surface = face.Surface
    radius = getattr(surface, 'Radius', 0)
    if not TOL < radius < thickness / 3:
        return False
    box = face.BoundBox
    if not (box.ZMax <= radius + TOL or box.ZMin >= thickness-radius-TOL):
        return False
    u0,u1,v0,v1 = face.ParameterRange
    u,v = (u0+u1)/2,(v0+v1)/2
    point = face.valueAt(u,v)
    if isinstance(surface, Part.Cylinder):
        if abs(surface.Axis.z) > ANG_TOL:
            return False
        radial = point-surface.Center
        radial -= surface.Axis * radial.dot(surface.Axis)
    elif isinstance(surface, Part.Sphere):
        radial = point-surface.Center
    else:
        return False
    return face.normalAt(u,v).dot(radial) > 0  # Convex edge, not a side bore.


def bspline_taper_angle(face, samples=5):
    """Taper angle of a B-spline face that keeps one slope everywhere (a chamfer
    strip or corner written as a spline), else None. The ruled-taper
    reconstruction check later proves the face really is a taper."""
    u0, u1, v0, v1 = face.ParameterRange
    angles = [math.degrees(math.asin(min(1.0, abs(face.normalAt(u0 + (u1 - u0) * (i + 0.5) / samples,
                                                                 v0 + (v1 - v0) * (j + 0.5) / samples).z))))
              for i in range(samples) for j in range(samples)]
    if max(angles) - min(angles) > TAPER_ANGLE_TOL_DEG:
        return None
    angle = sum(angles) / len(angles)
    return angle if 1 < angle < 89 else None


def taper_angle(face):
    """Taper angle in degrees, measured like a cone's semi-angle."""
    if isinstance(face.Surface, Part.Cone):
        return math.degrees(abs(face.Surface.SemiAngle))
    if isinstance(face.Surface, Part.BSplineSurface):
        return bspline_taper_angle(face)
    return math.degrees(math.asin(abs(face.normalAt(0, 0).z)))


def canonical_edge(edge, samples=16):
    """Exact line or arc for a spline edge that is geometrically one, ending on the
    original vertices; otherwise the edge unchanged, for validate_edges to reject."""
    if isinstance(edge.Curve, (Part.Line, Part.Circle)) or edge.isClosed():
        return edge
    p0, p1 = edge.FirstParameter, edge.LastParameter
    points = [edge.valueAt(p0 + (p1 - p0) * k / samples) for k in range(samples + 1)]
    ends = [vertex.Point for vertex in edge.Vertexes]
    a = min(ends, key=lambda p: (p - points[0]).Length)
    b = min(ends, key=lambda p: (p - points[-1]).Length)
    chord = b - a
    if chord.Length <= TOL:
        return edge
    direction = App.Vector(chord).normalize()
    if (abs(chord.Length - edge.Length) < EXACT_FIT_TOL
            and max((p - a).cross(direction).Length for p in points) < EXACT_FIT_TOL):
        return Part.makeLine(a, b)
    try:
        arc = Part.Arc(a, points[samples // 2], b).toShape()
    except Part.OCCError:  # collinear points: not an arc
        return edge
    circle = arc.Curve
    if (abs(arc.Length - edge.Length) < EXACT_FIT_TOL
            and max(abs((p - circle.Center).Length - circle.Radius) for p in points) < EXACT_FIT_TOL):
        return arc
    return edge


def level_wires(faces, level, bounds, closing_lines=None):
    """Closed contours of the taper faces' edges at one level. An open contour is
    closed along the panel edge it ends on; if closing_lines is a list, each such
    line is recorded there as (start, end, outward normal of that panel edge)."""
    edges = []
    for face in faces:
        for edge in face.Edges:
            if edge.Length > TOL and abs(edge.BoundBox.ZMin-level)<TOL and abs(edge.BoundBox.ZMax-level)<TOL:
                if not any(edge.isSame(e) for e in edges): edges.append(edge)
    edges = [canonical_edge(e) for e in edges]
    wires = []
    for chain in Part.sortEdges(edges, TOL):
        wire = Part.Wire(chain)
        if not wire.isClosed():
            ends=[]
            for edge in chain:
                for vertex in edge.Vertexes:
                    point=vertex.Point
                    if not any((point-p).Length<TOL for p in ends): ends.append(point)
            ends=[p for p in ends if sum(any((v.Point-p).Length<TOL for v in e.Vertexes) for e in chain)==1]
            if len(ends)!=2:raise ExportError('An open taper does not have two boundary endpoints.')
            a,b=ends
            sides=[outward for axis, bound, outward in [('x',bounds.XMin,App.Vector(-1,0,0)),('x',bounds.XMax,App.Vector(1,0,0)),
                                                        ('y',bounds.YMin,App.Vector(0,-1,0)),('y',bounds.YMax,App.Vector(0,1,0))]
                   if abs(getattr(a,axis)-bound)<TOL and abs(getattr(b,axis)-bound)<TOL]
            if not sides:raise ExportError('Open taper ends do not lie on one panel edge.')
            wire=Part.Wire(chain+[Part.makeLine(a,b)])
            if closing_lines is not None:closing_lines.append((a,b,sides[0]))
        if not wire.isClosed():raise ExportError('Taper boundary is not closed.')
        wires.append(wire)
    return wires


def continue_past_panel_edge(wire, closing_lines):
    """A taper contour for the reconstruction check's ruled loft, never for drawings.

    A ruled loft is the cut's exact cone only where the matching arcs at the two
    depths span equal angles. A panel edge that cuts the cone off its axis (for
    example a paired pull centred on the gap between two panels) ends the arcs at
    a different angle at each depth, so the loft falls short of the cone. Each arc
    that ends on the panel edge is therefore continued, outside the panel, to an
    angle that does not depend on its radius: along the edge when its centre lies
    beyond the edge, otherwise straight out across it. Pieces of one circle that
    then meet are joined, and the closing line follows (it disappears where the
    ends meet). The blank has no material outside the panel, so only the loft's
    error changes. Within PANEL_EDGE_CONTINUE_MIN of the edge the plain loft's
    error is negligible and new edges that close to the blank can break the
    boolean, so such arcs are left alone. Returns the same wire object when
    nothing needs to change."""
    edges = wire.OrderedEdges
    closing = outward = None
    for start, end, normal in closing_lines:
        for edge in edges:
            points = [v.Point for v in edge.Vertexes]
            if isinstance(edge.Curve, Part.Line) and len(points) == 2 and (
                    ((points[0] - start).Length < TOL and (points[1] - end).Length < TOL) or
                    ((points[0] - end).Length < TOL and (points[1] - start).Length < TOL)):
                closing, outward = edge, normal
                break
        if closing is not None:
            break
    if closing is None:
        return wire
    a, b = closing.Vertexes[0].Point, closing.Vertexes[-1].Point
    along = b - a
    along.normalize()
    moved = []
    result = []
    for edge in edges:
        if edge.isSame(closing):
            continue
        if not isinstance(edge.Curve, Part.Circle) or edge.isClosed():
            result.append(edge)
            continue
        centre, radius = edge.Curve.Center, edge.Curve.Radius
        ends = [edge.Vertexes[0].Point, edge.Vertexes[-1].Point]
        targets = []
        for point in ends:
            target = point
            if (point - a).Length < TOL or (point - b).Length < TOL:
                beyond = (centre - point).dot(outward)  # how far the centre lies past the edge
                side = (point - centre).dot(along)
                if beyond >= PANEL_EDGE_CONTINUE_MIN and abs(side) > TOL:
                    target = centre + along * math.copysign(radius, side)
                elif -beyond >= PANEL_EDGE_CONTINUE_MIN and radius + beyond >= PANEL_EDGE_CONTINUE_MIN:
                    target = centre + outward * radius
            if (target - point).Length > TOL:
                moved.append((point, target))
            targets.append(target)
        if all((t - p).Length <= TOL for t, p in zip(targets, ends)):
            result.append(edge)
        elif (targets[0] - targets[1]).Length <= TOL:
            result.append(Part.makeCircle(radius, centre, Z))
        else:
            middle = edge.valueAt((edge.FirstParameter + edge.LastParameter) / 2)
            result.append(Part.Arc(targets[0], middle, targets[1]).toShape())
    if not moved:
        return wire
    result = join_arcs_at(result, [target for _, target in moved])

    def continued(point):
        return next((target for p, target in moved if (p - point).Length < TOL), point)

    start, end = continued(a), continued(b)
    if (start - end).Length > TOL:
        result.append(Part.makeLine(start, end))
    chains = Part.sortEdges(result, TOL)
    if len(chains) != 1:
        return wire
    continued_wire = Part.Wire(chains[0])
    return continued_wire if continued_wire.isClosed() else wire


def join_arcs_at(edges, points):
    """Join each pair of arcs of one circle that meet at one of points into one arc,
    or into the whole circle when their other ends meet too."""
    edges = list(edges)
    while True:
        arcs = [e for e in edges if isinstance(e.Curve, Part.Circle) and not e.isClosed()]
        pair = None
        for i, first in enumerate(arcs):
            for second in arcs[i + 1:]:
                if ((first.Curve.Center - second.Curve.Center).Length > TOL
                        or abs(first.Curve.Radius - second.Curve.Radius) > TOL):
                    continue
                ends1 = [v.Point for v in first.Vertexes]
                ends2 = [v.Point for v in second.Vertexes]
                meet = [p for p in ends1 if any((p - q).Length < TOL for q in ends2)
                        and any((p - t).Length < TOL for t in points)]
                if len(meet) == 1:
                    pair = first, second, meet[0], ends1, ends2
                    break
            if pair:
                break
        if pair is None:
            return edges
        first, second, meet, ends1, ends2 = pair
        other1 = next(p for p in ends1 if (p - meet).Length >= TOL)
        other2 = next(p for p in ends2 if (p - meet).Length >= TOL)
        if (other1 - other2).Length < TOL:
            joined = Part.makeCircle(first.Curve.Radius, first.Curve.Center, Z)
        else:
            joined = Part.Arc(other1, meet, other2).toShape()
        edges = [e for e in edges if not (e.isSame(first) or e.isSame(second))] + [joined]


def taper_cutter(lower, upper, lower_closing=(), upper_closing=()):
    """Ruled solids between a taper's two contours, for the reconstruction check only:
    (cutter, plain loft). The cutter is the plain loft unless the contours continued
    past a panel edge give one valid solid."""
    loft = Part.makeLoft([lower, upper], True, True)
    try:
        low = continue_past_panel_edge(lower, lower_closing)
        high = continue_past_panel_edge(upper, upper_closing)
        if low is lower and high is upper:
            return loft, loft
        # Start whole-circle contours at angle 0, so the circles at both depths start
        # at the same angle and the ruled lines between them stay radial.
        low, high = [Part.Wire([Part.makeCircle(w.Edges[0].Curve.Radius, w.Edges[0].Curve.Center, Z)])
                     if len(w.Edges) == 1 and isinstance(w.Edges[0].Curve, Part.Circle) and w.Edges[0].isClosed()
                     else w for w in (low, high)]
        cut = Part.makeLoft([low, high], True, True)
        if cut.isValid() and len(cut.Solids) == 1:
            return cut, loft
    except Exception:  # Part.OCCError or FreeCAD's own RuntimeError: keep the plain loft
        pass
    return loft, loft


def extract_tapers(shape, faces):
    # Group by exact levels within TOL. The levels themselves are passed on, so
    # level_wires matches edges at the true depth rather than a rounded one.
    groups=[]
    for face in faces:
        angle=taper_angle(face)
        fb=face.optimalBoundingBox()
        for group in groups:
            if abs(group[0]-fb.ZMin)<TOL and abs(group[1]-fb.ZMax)<TOL and abs(group[2]-angle)<TAPER_ANGLE_TOL_DEG:
                group[3].append(face);break
        else:
            groups.append([fb.ZMin,fb.ZMax,angle,[face]])
    bounds=shape.optimalBoundingBox()
    thickness=bounds.ZLength
    results=[]
    for low,high,angle,fs in groups:
        angle=round(angle,6)+0.0  # report e.g. 44.99999999997 as 45
        lower_closing,upper_closing=[],[]
        lower=level_wires(fs,low,bounds,lower_closing);upper=level_wires(fs,high,bounds,upper_closing)
        if not lower or len(lower)!=len(upper):raise ExportError('Taper boundary counts do not match.')
        used=set()
        for lo in lower:
            options=[(i,hi) for i,hi in enumerate(upper) if i not in used]
            i,hi=min(options,key=lambda pair:(Part.Face(lo).CenterOfMass-Part.Face(pair[1]).CenterOfMass).Length)
            used.add(i)
            # Ruled solid between the exact edge contours of the source faces,
            # continued past a panel edge where that keeps it on the cone.
            cut,loft=taper_cutter(lo,hi,lower_closing,upper_closing)
            if not cut.isValid() or len(cut.Solids)!=1:raise ExportError('Taper contours do not form one valid solid.')
            lowface,highface=Part.Face(lo),Part.Face(hi)
            wide,narrow=(lowface,highface) if lowface.Area>highface.Area else (highface,lowface)
            rear=wide.CenterOfMass.z<narrow.CenterOfMass.z
            side='BACK' if rear else 'FRONT'
            start=wide.CenterOfMass.z if rear else thickness-wide.CenterOfMass.z
            end=narrow.CenterOfMass.z if rear else thickness-narrow.CenterOfMass.z
            if end<=start+TOL:raise ExportError('Taper cutting depths are reversed.')
            results.append({'solid':cut,'loft':loft,'wide':wide,'narrow':narrow,'angle':angle,'side':side,'start':start,'end':end})
    return results


def manufacturing_footprint(shape, horizontal, round_faces):
    projected=[flat_face(f) for f in horizontal]
    # Include exact cross sections at the finishing-radius transitions. Broad
    # faces alone are inset by a roundover and would make the blank too small.
    thickness=shape.optimalBoundingBox().ZLength
    levels={round(thickness/2,6)}
    for face in round_faces:
        levels.update([round(face.BoundBox.ZMin,6),round(face.BoundBox.ZMax,6)])
    for level in sorted(levels):
        if TOL<level<thickness-TOL:
            wires=shape.slice(Z,level)
            if wires:
                section=Part.makeFace(wires,'Part::FaceMakerBullseye')
                for face in section.Faces:projected.append(flat_face(face))
    footprint=projected[0].multiFuse(projected[1:]).removeSplitter() if len(projected)>1 else projected[0]
    if len(footprint.Faces)!=1:raise ExportError('The board silhouette is not one connected planar region.')
    return footprint.Faces[0]


def rebuild_part(blank, removals, shape):
    """The part rebuilt from its operations: (solid, volume it has that the part
    does not, volume the part has that it does not)."""
    reconstructed = blank
    if removals:
        cutters = removals[0].multiFuse(removals[1:]) if len(removals) > 1 else removals[0]
        reconstructed = blank.cut(cutters)
    return reconstructed, reconstructed.cut(shape).Volume, shape.cut(reconstructed).Volume


def analyse_solid(solid, label, normal=None):
    shape = orient_pull_front(flatten_solid(solid, normal))
    bb = shape.optimalBoundingBox()
    thickness = bb.ZLength
    volume_tolerance = max(1e-4, shape.Volume * 1e-9)
    horizontal = []
    cones = []
    cylinders = []
    taper_faces, round_faces = [], []
    for i, face in enumerate(shape.Faces):
        surface = face.Surface
        if isinstance(surface, Part.Plane):
            nz = abs(face.normalAt(0, 0).z)
            if nz > 1 - ANG_TOL:
                horizontal.append(face)
            elif nz > ANG_TOL:
                taper_faces.append(face)
        elif isinstance(surface, (Part.Cylinder, Part.Cone)):
            if abs(surface.Axis.z) < 1 - ANG_TOL:
                if exterior_round(face, thickness):
                    round_faces.append(face); continue
                raise ExportError('Face %d is an unsupported side/angled hole.' % (i + 1))
            if tapered_cone(face):
                taper_faces.append(face)
            else:
                (cones if isinstance(surface, Part.Cone) else cylinders).append(face)
        elif isinstance(surface, Part.Sphere) and exterior_round(face, thickness):
            round_faces.append(face)
        elif isinstance(surface, Part.BSplineSurface) and bspline_taper_angle(face) is not None:
            taper_faces.append(face)
        else:
            raise ExportError('Face %d uses unsupported %s geometry.' % (i + 1, type(surface).__name__))
    if not horizontal:
        raise ExportError('No broad planar faces found.')
    silhouette = manufacturing_footprint(shape, horizontal, round_faces)
    outline_face = face_of_wire(silhouette.OuterWire)
    blank = outline_face.extrude(App.Vector(0, 0, thickness))
    operations = [operation('OUTLINE', 'FRONT', outline_face)]
    removals = []
    notes = []
    # Inner loops of the complete silhouette are genuine through-openings.
    for wire in silhouette.Wires:
        if wire.isSame(silhouette.OuterWire):
            continue
        face = face_of_wire(wire)
        circle = circle_of_wire(wire)
        operations.append(operation('HOLE' if circle else 'CUTOUT', 'FRONT', face,
                                    diameter=2 * circle[1] if circle else None))
        removals.append(face.extrude(App.Vector(0, 0, thickness)))
    # Planar recess floors. Keep true islands, but do not turn deeper holes into
    # islands on the pocket layer: the pocket may safely pass over those voids.
    for face in horizontal:
        level = face.CenterOfMass.z
        if level <= TOL or level >= thickness - TOL:
            continue
        is_front = face.normalAt(0, 0).z > 0
        side = 'FRONT' if is_front else 'BACK'
        depth = thickness - level if is_front else level
        direction = App.Vector(0, 0, depth if is_front else -depth)
        region = face_of_wire(face.OuterWire)
        for wire in face.Wires:
            if wire.isSame(face.OuterWire):
                continue
            island = face_of_wire(wire)
            if island.extrude(direction).common(shape).Volume > volume_tolerance:
                region = region.cut(island)
        if len(region.Faces) != 1:
            raise ExportError('A pocket floor could not be resolved into one region.')
        removal = region.extrude(direction)
        if removal.common(shape).Volume > volume_tolerance:
            raise ExportError('An internal floor is covered by solid material (undercut or enclosed cavity).')
        circle = circle_of_wire(region.Faces[0].OuterWire) if len(region.Wires) == 1 else None
        operations.append(operation('HOLE' if circle else 'POCKET', side, region.Faces[0],
                                    depth=depth, diameter=2 * circle[1] if circle else None))
        removals.append(removal)
    # Support true drill-point cones, not countersinks/tapers. Record both the
    # full-diameter depth and the deepest point, from the original board face.
    for cone in cones:
        umin, umax, _, _ = cone.ParameterRange
        if abs(umax - umin - 2 * math.pi) > ANG_TOL:
            raise ExportError('Partial conical surface is unsupported.')
        circles = [e.Curve for e in cone.Edges if e.Length > TOL and isinstance(e.Curve, Part.Circle) and e.Curve.Radius > TOL and e.isClosed()]
        if len(circles) != 1:
            raise ExportError('Countersinks or truncated cones are unsupported; only complete drill tips are supported.')
        base = circles[0].Center
        radius = circles[0].Radius
        zlo, zhi = cone.BoundBox.ZMin, cone.BoundBox.ZMax
        is_front = abs(base.z - zhi) < TOL
        apex = zlo if is_front else zhi
        if abs(apex - base.z) < TOL:
            raise ExportError('Degenerate drill tip.')
        matching = []
        for cylinder in cylinders:
            c = cylinder.Surface
            cu, cv, _, _ = cylinder.ParameterRange
            if abs(cv - cu - 2 * math.pi) > ANG_TOL or abs(c.Radius - radius) > TOL:
                continue
            axis_origin = c.Center
            if math.hypot(axis_origin.x - base.x, axis_origin.y - base.y) > TOL:
                continue
            end = cylinder.BoundBox.ZMin if is_front else cylinder.BoundBox.ZMax
            if abs(end - base.z) < TOL:
                matching.append(cylinder)
        if len(matching) != 1:
            raise ExportError('Drill tip does not have one matching cylindrical bore.')
        side = 'FRONT' if is_front else 'BACK'
        depth = thickness - base.z if is_front else base.z
        tip_depth = thickness - apex if is_front else apex
        if depth <= TOL or tip_depth >= thickness - TOL:
            raise ExportError('Drill tip crosses the opposite face or has ambiguous depth.')
        direction = App.Vector(0, 0, -1 if is_front else 1)
        tip_solid = Part.makeCone(radius, 0, abs(base.z - apex), base, direction)
        shaft = Part.makeCylinder(radius, depth, base, -direction)
        removal = shaft.fuse(tip_solid)
        if removal.common(shape).Volume > volume_tolerance:
            raise ExportError('A drill-tip hole cannot be reached from the broad face.')
        wire = Part.Wire([Part.makeCircle(radius, App.Vector(base.x, base.y, 0))])
        operations.append(operation('HOLE', side, Part.Face(wire), depth, 2 * radius, tip_depth))
        removals.append(removal)
        notes.append('Hole D%s: full diameter to %s mm; drill tip to %s mm, both measured from the original %s surface.' %
                     (mm(2 * radius), mm(depth), mm(tip_depth), side.lower()))
    plain_lofts = []  # (index in removals, plain loft) to retry with if the rebuild breaks
    for taper in extract_tapers(shape, taper_faces):
        if taper['loft'] is not taper['solid']:
            plain_lofts.append((len(removals), taper['loft']))
        removals.append(taper['solid'])
        # The wide mouth must also be clear up to the entry face. For open
        # notches this void joins the stock edge and is not an inner floor wire.
        if taper['start'] > TOL:
            direction=App.Vector(0,0,-taper['start'] if taper['side']=='BACK' else taper['start'])
            entry=taper['wide'].extrude(direction)
            if entry.common(shape).Volume > volume_tolerance:
                raise ExportError('The tapered cut cannot be entered from its wide side.')
            removals.append(entry)
        for contour, reference in [('wide', False), ('narrow', True)]:
            op=operation('TAPER',taper['side'],taper[contour],depth=taper['end'])
            op.update({'angle_deg':taper['angle'],'start_depth_mm':taper['start'],
                       'end_depth_mm':taper['end'],'entry_clearance_depth_mm':taper['start'],'contour':contour,'reference_only':reference})
            op['layer']=('REFERENCE_' if reference else '')+'TAPER_%sDEG_%s_START_%sMM_END_%sMM' % (token(taper['angle']),contour.upper(),token(taper['start']),token(taper['end']))
            operations.append(op)
        notes.append('%s: %s degree tapered cut, wide contour at depth %s mm, narrow contour at depth %s mm. Preserve the front land; use the exact STEP solid to set the cutter.' % (taper['side'],mm(taper['angle']),mm(taper['start']),mm(taper['end'])))
    for face in round_faces:
        if not isinstance(face.Surface,Part.Cylinder):continue
        radius=face.Surface.Radius; box=face.BoundBox
        if min(box.XLength,box.YLength)<=TOL:continue
        side='FRONT' if box.ZMin>thickness/2 else 'BACK'
        region=Part.Face(rectangle_wire(box.XLength,box.YLength,box.XMin,box.YMin))
        op=operation('EDGE_ROUND',side,region,depth=radius)
        op.update({'radius_mm':radius,'reference_only':True})
        op['layer']='REFERENCE_EDGE_ROUND_R%sMM'%token(radius);operations.append(op)
    if round_faces:
        notes.append('Rounded edge finishing regions are reference envelopes, not cutting paths. Exact rounded geometry is retained in STEP and the flat 3D parts.')
    # Strong guard against missed, invented or incorrectly oriented features.
    # Rebuild the final part from exactly these interpreted operations.
    reconstructed, extra, missing = rebuild_part(blank, removals, shape)
    if plain_lofts and (not reconstructed.isValid() or min(extra, missing) < -volume_tolerance):
        # A continued taper cutter broke the boolean: retry with the plain lofts.
        retry = list(removals)
        for index, loft in plain_lofts:
            retry[index] = loft
        reconstructed, extra, missing = rebuild_part(blank, retry, shape)
    roundover_volume=0.0
    if round_faces and extra>volume_tolerance:
        envelopes=[]
        for face in round_faces:
            box=face.BoundBox
            envelopes.append(Part.makeBox(max(box.XLength, TOL)+2*TOL,max(box.YLength,TOL)+2*TOL,max(box.ZLength,TOL)+2*TOL,
                                         App.Vector(box.XMin-TOL,box.YMin-TOL,box.ZMin-TOL)))
        envelope=envelopes[0].multiFuse(envelopes[1:]) if len(envelopes)>1 else envelopes[0]
        residual=reconstructed.cut(shape)
        extra=residual.cut(envelope).Volume
        roundover_volume=residual.Volume-extra
    # A broken boolean gives an invalid solid whose volumes can be negative and
    # would pass the comparison below whatever the operations are.
    if not reconstructed.isValid() or min(extra, missing) < -volume_tolerance:
        raise ExportError('The operations could not be checked: rebuilding this part from them failed.')
    if max(extra, missing) > volume_tolerance:
        raise ExportError('Operations do not reproduce this solid outside the labelled rounded-edge finishing regions (unexplained %.6f mm3, overcut %.6f mm3).' % (extra, missing))
    return {'label': label, 'shape': shape, 'width_mm': bb.XLength,
            'height_mm': bb.YLength, 'thickness_mm': thickness,
            'operations': operations, 'notes': sorted(set(notes)),
            'verification': {'unexplained_volume_mm3': extra, 'overcut_volume_mm3': missing,
                             'tolerance_mm3': volume_tolerance, 'roundover_finishing_volume_mm3': roundover_volume,
                             'method': 'Prismatic and ruled-taper reconstruction; remaining removal must lie within convex roundover envelopes.'}}


def bulge_extremes(x1, y1, x2, y2, bulge):
    """Axis-extreme points of a DXF bulge arc that lie inside its sweep."""
    chord = math.hypot(x2 - x1, y2 - y1)
    if abs(bulge) < 1e-14 or chord <= TOL:
        return []
    sweep = 4 * math.atan(bulge)
    offset = chord * (1 - bulge * bulge) / (4 * bulge)
    cx = (x1 + x2) / 2 - offset * (y2 - y1) / chord
    cy = (y1 + y2) / 2 + offset * (x2 - x1) / chord
    radius = math.hypot(x1 - cx, y1 - cy)
    start = math.atan2(y1 - cy, x1 - cx)
    points = []
    for quarter in range(4):
        angle = quarter * math.pi / 2
        travel = (angle - start) % (2 * math.pi) if sweep > 0 else (start - angle) % (2 * math.pi)
        if travel <= abs(sweep):
            points.append((cx + radius * math.cos(angle), cy + radius * math.sin(angle)))
    return points


# Minimal ASCII DXF writer. Geometry stays analytic: closed LWPOLYLINE with
# circular-arc bulges, plus CIRCLE for round holes. No tessellation or splines.
class Dxf:
    def __init__(self, palette=None):
        self.entities = []
        self.palette = palette
        self.layers = {'0': 7, 'LABELS': 7}

    def add_wire(self, wire, layer, dx=0, dy=0, mirror_width=None):
        validate_edges(wire)
        self.layers[layer] = 7  # Final colour is assigned consistently when saving.
        circle = circle_of_wire(wire)
        def point(p):
            return (dx + (mirror_width - p.x if mirror_width is not None else p.x), dy + p.y)
        if circle:
            center, radius = circle
            x, y = point(center)
            self.entities.append([(0, 'CIRCLE'), (100, 'AcDbEntity'), (8, layer), (100, 'AcDbCircle'),
                                  (10, x), (20, y), (30, 0), (40, radius)])
            return
        vertices = []
        last = None
        first = None
        for edge in wire.OrderedEdges:
            if edge.Length <= TOL:
                continue
            a, b = edge.valueAt(edge.FirstParameter), edge.valueAt(edge.LastParameter)
            if edge.Orientation == 'Reversed':
                a, b = b, a
            if last is not None and (a - last).Length > TOL:
                raise ExportError('Wire edge ordering is not continuous.')
            if first is None:
                first = a
            last = b
            bulge = 0.0
            if isinstance(edge.Curve, Part.Circle):
                mid = edge.valueAt((edge.FirstParameter + edge.LastParameter) / 2)
                cross = (mid - a).cross(b - mid).z
                if abs(cross) < 1e-12:
                    raise ExportError('Circular arc direction is ambiguous.')
                sweep = edge.Length / edge.Curve.Radius
                bulge = math.copysign(math.tan(sweep / 4), cross)
                if mirror_width is not None:
                    bulge = -bulge
            x, y = point(a)
            vertices.append((x, y, bulge))
        if first is None or (last - first).Length > TOL:
            raise ExportError('Export polyline did not close.')
        tags = [(0, 'LWPOLYLINE'), (100, 'AcDbEntity'), (8, layer), (100, 'AcDbPolyline'),
                (90, len(vertices)), (70, 1), (38, 0)]
        for x, y, bulge in vertices:
            tags += [(10, x), (20, y)]
            if bulge:
                tags += [(42, bulge)]
        self.entities.append(tags)

    def add_text(self, text, x, y, height=5):
        # DXF text is ASCII; labels are metadata and never cutting geometry.
        text = str(text).encode('ascii', 'replace').decode().replace('\n', ' ')
        if not text.strip():
            return
        self.entities.append([(0, 'TEXT'), (100, 'AcDbEntity'), (8, 'LABELS'), (100, 'AcDbText'),
                              (10, x), (20, y), (30, 0), (40, height), (1, text), (7, 'STANDARD')])

    def add_line(self, a, b, layer='REFERENCE_GRAIN'):
        self.layers[layer] = 7  # Final colour is assigned consistently when saving.
        self.entities.append([(0, 'LINE'), (100, 'AcDbEntity'), (8, layer),
                              (100, 'AcDbLine'), (10, a[0]), (20, a[1]), (30, 0),
                              (11, b[0]), (21, b[1]), (31, 0)])

    def save(self, path):
        palette = self.palette if self.palette is not None else make_layer_palette(self.layers)
        for layer in self.layers:
            if layer not in palette:
                raise ExportError('No colour assigned for layer %s.' % layer)
            self.layers[layer] = palette[layer]['aci']
        # AC1018 readers (VCarve, ODA-based CAM) need the full R2000+ object
        # graph: entities owned by a *Model_Space block record, BLOCKS for
        # model/paper space, layouts and a root dictionary. Without them the
        # reader stops at ENTITIES and imports nothing.
        handles = itertools.count(0x20)
        def handle():
            return '%X' % next(handles)
        model_record, paper_record = handle(), handle()
        model_layout, paper_layout = handle(), handle()
        root_dict, group_dict, layout_dict = handle(), handle(), handle()
        plot_styles, plot_style_normal = handle(), handle()

        def table(name, records, subclass=None):
            owner = handle()
            tags = [(0, 'TABLE'), (2, name), (5, owner), (330, '0'), (100, 'AcDbSymbolTable'), (70, len(records))]
            if subclass:
                tags.append((100, subclass))
            for record_handle, body in records:
                tags += [(0, name), (105 if name == 'DIMSTYLE' else 5, record_handle or handle()),
                         (330, owner), (100, 'AcDbSymbolTableRecord')] + body
            return tags + [(0, 'ENDTAB')]

        xs, ys = [], []
        for entity in self.entities:
            values = dict(entity)
            radius = values.get(40, 0) if values[0] == 'CIRCLE' else 0
            for code, value in entity:
                if code in (10, 11):
                    xs += [value - radius, value + radius]
                elif code in (20, 21):
                    ys += [value - radius, value + radius]
            if values[0] == 'LWPOLYLINE':
                vertices = []
                for code, value in entity:
                    if code == 10:
                        vertices.append([value, 0.0, 0.0])
                    elif code == 20:
                        vertices[-1][1] = value
                    elif code == 42:
                        vertices[-1][2] = value
                following = vertices[1:] + (vertices[:1] if values.get(70, 0) & 1 else [])
                for (x1, y1, bulge), (x2, y2, _) in zip(vertices, following):
                    for x, y in bulge_extremes(x1, y1, x2, y2, bulge):
                        xs.append(x)
                        ys.append(y)
        xmin, xmax = (min(xs), max(xs)) if xs else (0.0, 1.0)
        ymin, ymax = (min(ys), max(ys)) if ys else (0.0, 1.0)
        view_height = max(ymax - ymin, (xmax - xmin) / 1.5, 1.0) * 1.1

        tables = table('VPORT', [(None, [(100, 'AcDbViewportTableRecord'), (2, '*Active'), (70, 0),
                                         (10, 0.0), (20, 0.0), (11, 1.0), (21, 1.0),
                                         (12, (xmin + xmax) / 2), (22, (ymin + ymax) / 2),
                                         (13, 0.0), (23, 0.0), (14, 10.0), (24, 10.0), (15, 10.0), (25, 10.0),
                                         (16, 0.0), (26, 0.0), (36, 1.0), (17, 0.0), (27, 0.0), (37, 0.0),
                                         (40, view_height), (41, 1.5), (42, 50.0), (43, 0.0), (44, 0.0),
                                         (50, 0.0), (51, 0.0), (71, 0), (72, 100), (73, 1), (74, 3),
                                         (75, 0), (76, 0), (77, 0), (78, 0)])])
        tables += table('LTYPE', [(None, [(100, 'AcDbLinetypeTableRecord'), (2, name), (70, 0), (3, text), (72, 65), (73, 0), (40, 0.0)])
                                  for name, text in (('ByBlock', ''), ('ByLayer', ''), ('CONTINUOUS', 'Solid line'))])
        layers = []
        for name, colour in sorted(self.layers.items()):
            body = [(100, 'AcDbLayerTableRecord'), (2, name), (70, 0), (62, colour), (6, 'CONTINUOUS')]
            if 'true_colour' in palette[name]:
                body.append((420, palette[name]['true_colour']))
            layers.append((None, body + [(370, -3), (390, plot_style_normal)]))
        tables += table('LAYER', layers)
        tables += table('STYLE', [(None, [(100, 'AcDbTextStyleTableRecord'), (2, 'STANDARD'), (70, 0), (40, 0.0),
                                          (41, 1.0), (50, 0.0), (71, 0), (42, 2.5), (3, 'txt')])])
        tables += table('VIEW', []) + table('UCS', [])
        tables += table('APPID', [(None, [(100, 'AcDbRegAppTableRecord'), (2, 'ACAD'), (70, 0)])])
        tables += table('DIMSTYLE', [(None, [(100, 'AcDbDimStyleTableRecord'), (2, 'STANDARD'), (70, 0)])],
                        'AcDbDimStyleTable')
        tables += table('BLOCK_RECORD', [(model_record, [(100, 'AcDbBlockTableRecord'), (2, '*Model_Space'), (340, model_layout)]),
                                         (paper_record, [(100, 'AcDbBlockTableRecord'), (2, '*Paper_Space'), (340, paper_layout)])])

        blocks = []
        for record, name, space in ((model_record, '*Model_Space', []), (paper_record, '*Paper_Space', [(67, 1)])):
            blocks += [(0, 'BLOCK'), (5, handle()), (330, record), (100, 'AcDbEntity')] + space + [
                       (8, '0'), (100, 'AcDbBlockBegin'), (2, name), (70, 0), (10, 0.0), (20, 0.0), (30, 0.0), (3, name),
                       (0, 'ENDBLK'), (5, handle()), (330, record), (100, 'AcDbEntity')] + space + [
                       (8, '0'), (100, 'AcDbBlockEnd')]

        entities = []
        for entity in self.entities:
            entities += [entity[0], (5, handle()), (330, model_record)] + list(entity[1:])
            if entity[0][1] == 'TEXT':
                entities.append((100, 'AcDbText'))

        def layout(own, name, record, order, flags):
            return [(0, 'LAYOUT'), (5, own), (330, layout_dict), (100, 'AcDbPlotSettings'), (1, ''), (4, 'A3'), (6, ''),
                    (40, 7.5), (41, 20.0), (42, 7.5), (43, 20.0), (44, 420.0), (45, 297.0), (46, 0.0), (47, 0.0),
                    (48, 0.0), (49, 0.0), (140, 0.0), (141, 0.0), (142, 1.0), (143, 1.0), (70, flags), (72, 1),
                    (73, 0), (74, 5), (7, ''), (75, 16), (76, 0), (77, 2), (78, 300), (147, 1.0), (148, 0.0),
                    (149, 0.0), (100, 'AcDbLayout'), (1, name), (70, 1), (71, order), (10, 0.0), (20, 0.0),
                    (11, 420.0), (21, 297.0), (12, 0.0), (22, 0.0), (32, 0.0), (14, xmin), (24, ymin), (34, 0.0),
                    (15, xmax), (25, ymax), (35, 0.0), (146, 0.0), (13, 0.0), (23, 0.0), (33, 0.0),
                    (16, 1.0), (26, 0.0), (36, 0.0), (17, 0.0), (27, 1.0), (37, 0.0), (76, 1), (330, record)]
        objects = [(0, 'DICTIONARY'), (5, root_dict), (330, '0'), (100, 'AcDbDictionary'), (281, 1),
                   (3, 'ACAD_GROUP'), (350, group_dict), (3, 'ACAD_LAYOUT'), (350, layout_dict),
                   (3, 'ACAD_PLOTSTYLENAME'), (350, plot_styles),
                   (0, 'DICTIONARY'), (5, group_dict), (330, root_dict), (100, 'AcDbDictionary'), (281, 1),
                   (0, 'DICTIONARY'), (5, layout_dict), (330, root_dict), (100, 'AcDbDictionary'), (281, 1),
                   (3, 'Layout1'), (350, paper_layout), (3, 'Model'), (350, model_layout),
                   (0, 'ACDBDICTIONARYWDFLT'), (5, plot_styles), (330, root_dict), (100, 'AcDbDictionary'), (281, 1),
                   (3, 'Normal'), (350, plot_style_normal), (100, 'AcDbDictionaryWithDefault'), (340, plot_style_normal),
                   (0, 'ACDBPLACEHOLDER'), (5, plot_style_normal), (330, plot_styles)]
        objects += layout(model_layout, 'Model', model_record, 0, 1024) + layout(paper_layout, 'Layout1', paper_record, 1, 0)

        tags = [(0, 'SECTION'), (2, 'HEADER'), (9, '$ACADVER'), (1, 'AC1018'), (9, '$DWGCODEPAGE'), (3, 'ANSI_1252'),
                (9, '$INSBASE'), (10, 0.0), (20, 0.0), (30, 0.0),
                (9, '$EXTMIN'), (10, xmin), (20, ymin), (30, 0.0), (9, '$EXTMAX'), (10, xmax), (20, ymax), (30, 0.0),
                (9, '$INSUNITS'), (70, 4), (9, '$MEASUREMENT'), (70, 1),
                (9, '$LUNITS'), (70, 2), (9, '$LUPREC'), (70, 6), (9, '$HANDSEED'), (5, handle()), (0, 'ENDSEC'),
                (0, 'SECTION'), (2, 'CLASSES'), (0, 'ENDSEC'),
                (0, 'SECTION'), (2, 'TABLES')] + tables + [(0, 'ENDSEC'),
                (0, 'SECTION'), (2, 'BLOCKS')] + blocks + [(0, 'ENDSEC'),
                (0, 'SECTION'), (2, 'ENTITIES')] + entities + [(0, 'ENDSEC'),
                (0, 'SECTION'), (2, 'OBJECTS')] + objects + [(0, 'ENDSEC'), (0, 'EOF')]
        with open(path, 'w', encoding='ascii', newline='\n') as stream:
            for code, value in tags:
                # Optional empty strings are omitted: some line-based readers
                # treat a blank value line as a premature end of file.
                if value == '':
                    continue
                # 12 decimal places preserve coordinates and arc bulges.
                value = ('%.12f' % value).rstrip('0').rstrip('.') if isinstance(value, float) else str(value)
                stream.write('%d\n%s\n' % (code, value))


# Standard DXF ACI colours with RGB equivalents; no external runtime dependency.
_LAYER_SWATCHES = (
    (162, '#0029a5'), (92, '#00a500'), (12, '#a50000'), (202, '#7c00a5'), (32, '#a55200'), (132, '#00a5a5'),
    (222, '#a5007c'), (52, '#a5a500'), (112, '#00a552'), (182, '#2900a5'), (72, '#52a500'), (242, '#a50029'),
    (22, '#a52900'), (42, '#a57c00'), (62, '#7ca500'), (82, '#29a500'), (102, '#00a529'), (122, '#00a57c'),
    (142, '#007ca5'), (152, '#0052a5'), (172, '#0000a5'), (192, '#5200a5'), (212, '#a500a5'), (232, '#a50052'),
    (14, '#7f0000'), (24, '#7f1f00'), (34, '#7f3f00'), (44, '#7f5f00'), (54, '#7f7f00'), (64, '#5f7f00'),
    (74, '#3f7f00'), (84, '#1f7f00'), (94, '#007f00'), (104, '#007f1f'), (114, '#007f3f'), (124, '#007f5f'),
    (134, '#007f7f'), (144, '#005f7f'), (154, '#003f7f'), (164, '#001f7f'), (174, '#00007f'), (184, '#1f007f'),
    (194, '#3f007f'), (204, '#5f007f'), (214, '#7f007f'), (224, '#7f005f'), (234, '#7f003f'), (244, '#7f001f'),
    (13, '#a55252'), (23, '#a56752'), (33, '#a57c52'), (43, '#a59152'), (53, '#a5a552'), (63, '#91a552'),
    (73, '#7ca552'), (83, '#67a552'), (93, '#52a552'), (103, '#52a567'), (113, '#52a57c'), (123, '#52a591'),
    (133, '#52a5a5'), (143, '#5291a5'), (153, '#527ca5'), (163, '#5267a5'), (173, '#5252a5'), (183, '#6752a5'),
    (193, '#7c52a5'), (203, '#9152a5'), (213, '#a552a5'), (223, '#a55291'), (233, '#a5527c'), (243, '#a55267'),
    (15, '#7f3f3f'), (25, '#7f4f3f'), (35, '#7f5f3f'), (45, '#7f6f3f'), (55, '#7f7f3f'), (65, '#6f7f3f'),
    (75, '#5f7f3f'), (85, '#4f7f3f'), (95, '#3f7f3f'), (105, '#3f7f4f'), (115, '#3f7f5f'), (125, '#3f7f6f'),
    (135, '#3f7f7f'), (145, '#3f6f7f'), (155, '#3f5f7f'), (165, '#3f4f7f'), (175, '#3f3f7f'), (185, '#4f3f7f'),
    (195, '#5f3f7f'), (205, '#6f3f7f'), (215, '#7f3f7f'), (225, '#7f3f6f'), (235, '#7f3f5f'), (245, '#7f3f4f'),
    (10, '#ff0000'), (20, '#ff3f00'), (30, '#ff7f00'), (40, '#ffbf00'), (50, '#ffff00'), (60, '#bfff00'),
    (70, '#7fff00'), (80, '#3fff00'), (90, '#00ff00'), (100, '#00ff3f'), (110, '#00ff7f'), (120, '#00ffbf'),
    (130, '#00ffff'), (140, '#00bfff'), (150, '#007fff'), (160, '#003fff'), (170, '#0000ff'), (180, '#3f00ff'),
    (190, '#7f00ff'), (200, '#bf00ff'), (210, '#ff00ff'), (220, '#ff00bf'), (230, '#ff007f'), (240, '#ff003f'),
    (11, '#ff7f7f'), (21, '#ff9f7f'), (31, '#ffbf7f'), (41, '#ffdf7f'), (51, '#ffff7f'), (61, '#dfff7f'),
    (71, '#bfff7f'), (81, '#9fff7f'), (91, '#7fff7f'), (101, '#7fff9f'), (111, '#7fffbf'), (121, '#7fffdf'),
    (131, '#7fffff'), (141, '#7fdfff'), (151, '#7fbfff'), (161, '#7f9fff'), (171, '#7f7fff'), (181, '#9f7fff'),
    (191, '#bf7fff'), (201, '#df7fff'), (211, '#ff7fff'), (221, '#ff7fdf'), (231, '#ff7fbf'), (241, '#ff7f9f'),
    (16, '#4c0000'), (26, '#4c1300'), (36, '#4c2600'), (46, '#4c3900'), (56, '#4c4c00'), (66, '#394c00'),
    (76, '#264c00'), (86, '#134c00'), (96, '#004c00'), (106, '#004c13'), (116, '#004c26'), (126, '#004c39'),
    (136, '#004c4c'), (146, '#00394c'), (156, '#00264c'), (166, '#00134c'), (176, '#00004c'), (186, '#13004c'),
    (196, '#26004c'), (206, '#39004c'), (216, '#4c004c'), (226, '#4c0039'), (236, '#4c0026'), (246, '#4c0013'),
    (17, '#4c2626'), (27, '#4c2f26'), (37, '#4c3926'), (47, '#4c4226'), (57, '#4c4c26'), (67, '#424c26'),
    (77, '#394c26'), (87, '#2f4c26'), (97, '#264c26'), (107, '#264c2f'), (117, '#264c39'), (127, '#264c42'),
    (137, '#264c4c'), (147, '#26427e'), (157, '#26397e'), (167, '#262f7e'), (177, '#26267e'), (187, '#2f267e'),
    (197, '#39267e'), (207, '#42264c'), (217, '#4c264c'), (227, '#4c2642'), (237, '#4c2639'), (247, '#4c262f'),
)


def make_layer_palette(layer_names):
    """One colour per operation layer, shared across the entire export.

    ACI keeps the existing DXF format compatible. The matching RGB swatches
    are used by both previews. Never wrap the palette and duplicate a colour.
    """
    references = {
        '0': (7, '#222222'), 'LABELS': (7, '#222222'),
        'REFERENCE_SHEET': (8, '#808080'),
        'REFERENCE_MARGIN': (9, '#c0c0c0'),
        'REFERENCE_GRAIN': (253, '#999999'),
        'REFERENCE_OUTLINE': (251, '#656565'),
    }
    palette = {name: {'aci': aci, 'hex': colour} for name, (aci, colour) in references.items()}
    def order(name):
        rank = 0 if name == 'OUTLINE_THROUGH' else 1 if name == 'CUTOUT_THROUGH' else 2 if name.startswith('POCKET_') else 3
        numbers = tuple(float(n.replace('P', '.')) for n in re.findall(r'\d+(?:P\d+)?', name))
        return rank, numbers, name
    names = sorted(set(layer_names) - set(references), key=order)
    if len(names) > len(_LAYER_SWATCHES):
        raise ExportError('This export has more than %d distinct operation layers. Split it into smaller exports to keep every layer colour unique.' % len(_LAYER_SWATCHES))
    for name, (aci, colour) in zip(names, _LAYER_SWATCHES):
        palette[name] = {'aci': aci, 'hex': colour}
    return palette


def validate_layer_settings(settings):
    used = {}
    forbidden = set('<>/\\":;?*|=')
    for source, style in settings.items():
        name = str(style.get('name', source)).strip()
        if not name or len(name) > 255:
            raise ExportError('Layer names must contain between 1 and 255 characters.')
        if any(ord(c) < 32 or ord(c) > 126 or c in forbidden for c in name):
            raise ExportError('Layer name "%s" contains unsupported characters. Use plain letters, numbers, spaces, hyphens or underscores.' % name)
        if name.upper() in ('0', 'LABELS') or (name.upper().startswith('REFERENCE_') and not (name == source and source.startswith(('REFERENCE_TAPER_', 'REFERENCE_EDGE_ROUND_')))):
            raise ExportError('"%s" is reserved for reference geometry or labels.' % name)
        key = name.casefold()
        if key in used and used[key] != source:
            raise ExportError('Two different operations cannot both be named "%s". Give each operation layer a unique name.' % name)
        used[key] = source
        if not re.fullmatch(r'#[0-9A-Fa-f]{6}', str(style.get('hex', ''))):
            raise ExportError('Choose a valid colour for layer "%s".' % name)


def nearest_aci(colour):
    rgb = tuple(int(colour[i:i + 2], 16) for i in (1, 3, 5))
    candidates = list(_LAYER_SWATCHES) + [(250, '#000000'), (255, '#ffffff'), (8, '#808080'), (9, '#c0c0c0')]
    def difference(item):
        value = item[1]
        return sum((a - int(value[i:i + 2], 16)) ** 2 for a, i in zip(rgb, (1, 3, 5)))
    return min(candidates, key=difference)[0]


def apply_layer_settings(parts, settings):
    """Rename/style copied operations; preserve the recognition key and depths."""
    validate_layer_settings(settings)
    defaults = make_layer_palette(op.get('source_layer', op['layer']) for p in parts for op in p['operations'])
    result = []
    for part in parts:
        copy = dict(part)
        copy['operations'] = []
        for original in part['operations']:
            op = dict(original)
            source = original.get('source_layer', original['layer'])
            style = settings.get(source, {'name': source, 'hex': defaults[source]['hex']})
            op['source_layer'] = source
            op['layer'] = style['name'].strip()
            op['colour_hex'] = style['hex'].lower()
            copy['operations'].append(op)
        result.append(copy)
    return result


def apply_layout_styles(parts, sheets, styles):
    """Refresh operation styling without repeating validated sheet packing."""
    parts = apply_layer_settings(parts, styles)
    sheets = [dict(sheet, placements=[dict(placement, part=parts[placement['part_index']-1])
                                     for placement in sheet['placements']]) for sheet in sheets]
    return parts, sheets


def palette_for_parts(parts):
    operations = [op for p in parts for op in p['operations']]
    defaults = make_layer_palette(op.get('source_layer', op['layer']) for op in operations)
    palette = {name: dict(value) for name, value in defaults.items() if name in ('0', 'LABELS', 'REFERENCE_SHEET', 'REFERENCE_MARGIN', 'REFERENCE_GRAIN', 'REFERENCE_OUTLINE')}
    for op in operations:
        source = op.get('source_layer', op['layer'])
        colour = op.get('colour_hex', defaults[source]['hex'])
        if not re.fullmatch(r'#[0-9A-Fa-f]{6}', colour):
            raise ExportError('Invalid colour for layer %s.' % op['layer'])
        entry = {'aci': nearest_aci(colour), 'hex': colour.lower(), 'source_layer': source,
                 'true_colour': int(colour[1:], 16)}
        existing = palette.get(op['layer'])
        if existing is not None and existing != entry:
            raise ExportError('Conflicting colours or operations for layer %s.' % op['layer'])
        palette[op['layer']] = entry
    return palette


def layer_rgb(palette, layer):
    if layer not in palette:
        raise ExportError('No colour assigned for layer %s.' % layer)
    value = palette[layer]['hex'].lstrip('#')
    return tuple(int(value[i:i + 2], 16) / 255.0 for i in (0, 2, 4))


def grouped_face_operations(part, side):
    """Group all matching holes/pockets under one visible layer per part face.

    Hole names encode diameter, through/blind depth and any drill-tip depth.
    Coordinates/feature numbers are deliberately absent from that layer key.
    Front and back remain separate machining setups.
    """
    groups = {}
    for op in face_operations(part, side):
        groups.setdefault(op['layer'], []).append(op)
    return list(groups.items())


def face_operations(part, side):
    if side == 'FRONT':
        return [op for op in part['operations'] if op['side'] == 'FRONT']
    # Back drawings are physically flipped left-to-right. Outline is reference
    # only, and through-cuts are not duplicated as machining instructions.
    outline = dict(part['operations'][0])
    outline['layer'] = 'REFERENCE_OUTLINE'
    return [outline] + [op for op in part['operations'] if op['side'] == 'BACK']


def rectangle_wire(width, height, x=0, y=0):
    points = [App.Vector(x, y, 0), App.Vector(x + width, y, 0),
              App.Vector(x + width, y + height, 0), App.Vector(x, y + height, 0),
              App.Vector(x, y, 0)]
    return Part.Wire(Part.makePolygon(points).Edges)


def canonical_xy_face(face):
    """Rebuild analytic boundaries on one exact XY plane before booleans.

    Flattened model faces may still carry microscopic plane/placement offsets.
    Lines and circles stay analytic; only their already-flat Z coordinate is
    normalized. No mesh approximation or polygon sampling is involved.
    """
    def xy(point):
        return App.Vector(point.x, point.y, 0)

    def rebuild_wire(wire):
        validate_edges(wire)
        circle = circle_of_wire(wire)
        if circle:
            center, radius = circle
            return Part.Wire([Part.makeCircle(radius, xy(center), Z)])
        edges = []
        for edge in wire.OrderedEdges:
            if edge.Length <= TOL:
                continue
            start = xy(edge.valueAt(edge.FirstParameter))
            end = xy(edge.valueAt(edge.LastParameter))
            if edge.Orientation == 'Reversed':
                start, end = end, start
            if isinstance(edge.Curve, Part.Line):
                edges.append(Part.makeLine(start, end))
            elif isinstance(edge.Curve, Part.Circle):
                middle = xy(edge.valueAt((edge.FirstParameter + edge.LastParameter) / 2))
                edges.append(Part.Arc(start, middle, end).toShape())
            else:
                raise ExportError('Rebate boundary has unsupported %s geometry.' % type(edge.Curve).__name__)
        if not edges:
            raise ExportError('Rebate boundary is empty.')
        result = Part.Wire(edges)
        validate_edges(result)
        return result

    outer = face.OuterWire
    result = face_of_wire(rebuild_wire(outer))
    for wire in face.Wires:
        if not wire.isSame(outer):
            result = result.cut(face_of_wire(rebuild_wire(wire)))
    result = result.removeSplitter()
    if len(result.Faces) != 1 or not result.isValid():
        raise ExportError('Could not rebuild the original rebate on a common flat plane.')
    result = flat_face(result.Faces[0])
    if abs(result.Area - face.Area) > max(1e-5, face.Area * 1e-9):
        raise ExportError('Flattening the rebate changed its area beyond tolerance.')
    return result


def extend_rebate(face, outline, distance, part_shape, depth, side):
    """Continue clear straight exits without widening their endpoint spans.

    The finished solid decides whether a route to the stock edge is already
    clear to this operation's depth. This permits a shallow rebate to continue
    through a deeper adjacent cut, but never the reverse. No clipping around
    protected material is used: a blocked route is simply not an open exit.
    """
    if distance <= TOL:
        return face.copy(), 0
    if side not in ('FRONT', 'BACK') or depth is None or not math.isfinite(depth) or depth <= 0:
        raise ExportError('Rebate extension needs a valid machining face and pocket depth.')
    original = canonical_xy_face(face)
    stock_outline = canonical_xy_face(outline)
    bounds = part_shape.optimalBoundingBox()
    thickness = bounds.ZLength
    if depth > thickness + TOL:
        raise ExportError('Pocket depth exceeds the panel thickness.')
    volume_tolerance = max(1e-4, part_shape.Volume * 1e-9)
    area_tolerance = max(1e-5, original.Area * 1e-9)
    z_base = bounds.ZMax - depth if side == 'FRONT' else bounds.ZMin

    def band(a, b, direction, start, finish):
        points = [a + direction * start, b + direction * start,
                  b + direction * finish, a + direction * finish, a + direction * start]
        return face_of_wire(Part.Wire(Part.makePolygon(points).Edges))

    def machining_volume(region):
        copy = region.copy()
        copy.translate(App.Vector(0, 0, z_base))
        return copy.extrude(App.Vector(0, 0, depth))

    def is_clear(region):
        return machining_volume(region).common(part_shape).Volume <= volume_tolerance

    # A curved exterior exit is not silently approximated as a straight one.
    exterior_contact = original.common(stock_outline.OuterWire)
    for edge in exterior_contact.Edges:
        if edge.Length > TOL and not isinstance(edge.Curve, Part.Line):
            raise ExportError('Rebate extension has a curved outer-edge opening; only straight exits are supported.')
    pocket_prism = original.extrude(Z)
    additions, openings = [], []
    for edge in original.OuterWire.Edges:
        if edge.Length <= TOL or not isinstance(edge.Curve, Part.Line):
            continue
        a, b = edge.valueAt(edge.FirstParameter), edge.valueAt(edge.LastParameter)
        tangent = b - a
        tangent.normalize()
        left = App.Vector(-tangent.y, tangent.x, 0)
        middle = (a + b) * 0.5
        probe = max(TOL * 20, min(0.01, edge.Length * 0.01, distance * 0.1))
        left_inside = original.isInside(middle + left * probe, TOL, True)
        right_inside = original.isInside(middle - left * probe, TOL, True)
        if left_inside == right_inside:
            raise ExportError('Cannot determine the outward direction of a straight rebate boundary.')
        sign = -1 if left_inside else 1
        outward = left * sign
        # Measure the stock boundary in an edge-aligned coordinate frame. The
        # strip has EXACTLY the original opening's width: endpoints do not grow.
        angle = -math.degrees(math.atan2(tangent.y, tangent.x))
        stock_local = stock_outline.copy()
        stock_local.rotate(App.Vector(), Z, angle)
        level = left.dot(a)
        projected_reach = stock_local.BoundBox.YMax - level if sign > 0 else level - stock_local.BoundBox.YMin
        search_reach = max(0, projected_reach) + distance
        search_strip = band(a, b, outward, 0, search_reach)
        stock_in_strip = stock_outline.common(search_strip)
        stock_reach = 0.0
        if not stock_in_strip.isNull() and stock_in_strip.Area > area_tolerance:
            local = stock_in_strip.copy()
            local.rotate(App.Vector(), Z, angle)
            stock_reach = local.BoundBox.YMax - level if sign > 0 else level - local.BoundBox.YMin
        reach = max(0, stock_reach) + distance
        straight_extension = band(a, b, outward, 0, reach)
        if not is_clear(straight_extension):
            # This is an internal wall, not a clear exit. Never cut around it
            # into a hook or broaden a deeper cut into a shallower neighbour.
            continue
        overlap = max(TOL * 50, min(0.25, distance / 4, edge.Length / 10))
        patch = band(a, b, outward, -overlap, reach).extrude(Z)
        # Only the small joining overlap is trimmed; the outward extension is
        # untouched and remains straight. This handles rounded inside corners.
        inward = band(a, b, outward, -overlap, 0)
        trim = inward.cut(original)
        if not trim.isNull() and trim.Area > TOL * TOL:
            patch = patch.cut(trim.extrude(Z))
        additions.append(patch)
        openings.append({'a': a, 'b': b, 'normal': outward, 'reach': reach})
    if not openings:
        return face.copy(), 0

    # When TWO open sides meet, extend both straight sides to their common
    # outer corner. This fills the corner square/miter; it never widens a lone
    # opening into a T. Only convex, outward corners are eligible.
    corners = set()
    for index, first in enumerate(openings):
        for second in openings[index + 1:]:
            shared = next((p for p in (first['a'], first['b'])
                           if any((p - q).Length < TOL for q in (second['a'], second['b']))), None)
            if shared is None:
                continue
            n1, n2 = first['normal'], second['normal']
            determinant = n1.x * n2.y - n1.y * n2.x
            if abs(determinant) < ANG_TOL:
                continue
            other1 = first['b'] if (first['a'] - shared).Length < TOL else first['a']
            other2 = second['b'] if (second['a'] - shared).Length < TOL else second['a']
            if (other1 - shared).dot(n2) >= -TOL or (other2 - shared).dot(n1) >= -TOL:
                continue  # Keep concave corners; only fill an outward convex join.
            r1, r2 = first['reach'], second['reach']
            delta = App.Vector((r1 * n2.y - n1.y * r2) / determinant,
                               (n1.x * r2 - r1 * n2.x) / determinant, 0)
            key = tuple(round(v, 5) for v in shared)
            if key in corners:
                continue
            test = shared + (n1 + n2) * max(TOL * 20, min(0.01, distance / 10))
            if original.isInside(test, TOL, True):
                continue  # Concave material-facing corner, not an outer join.
            points = [shared, shared + n1 * r1, shared + delta, shared + n2 * r2, shared]
            corner = face_of_wire(Part.Wire(Part.makePolygon(points).Edges))
            if not corner.isValid():
                raise ExportError('Cannot form a straight outer corner for these rebate exits.')
            if not is_clear(corner):
                raise ExportError('Joining two rebate extensions at their corner would remove finished panel material.')
            additions.append(corner.extrude(Z))
            corners.add(key)

    united = pocket_prism.multiFuse(additions).removeSplitter()
    if not united.isValid() or len(united.Solids) != 1:
        raise ExportError('Straight rebate extension could not be joined (%d solids; %d faces; valid=%s).' %
                          (len(united.Solids), len(united.Faces), united.isValid()))
    if pocket_prism.cut(united).Volume > max(1e-5, pocket_prism.Volume * 1e-9):
        raise ExportError('Rebate extension lost part of the original pocket.')
    top_faces = [f for f in united.Faces if is_horizontal(f)
                 and f.normalAt(0, 0).z > 0 and abs(f.CenterOfMass.z - 1.0) < TOL]
    if len(top_faces) != 1:
        raise ExportError('Straight rebate extension has %d top regions; one is required.' % len(top_faces))
    expanded = canonical_xy_face(flat_face(top_faces[0]))
    if original.cut(expanded).Area > area_tolerance:
        raise ExportError('Straight extension lost part of the original 2D pocket.')
    if expanded.Area <= original.Area + area_tolerance:
        raise ExportError('The rebate extension did not add measurable clearance.')
    # Validate at the REAL machining depth against the finished solid. Extra
    # area may cross an already-deeper rebate but must remove no final material.
    if not is_clear(expanded):
        raise ExportError('Straight rebate extension would remove material from the finished panel.')
    for wire in expanded.Wires:
        validate_edges(wire)
    return expanded, len(openings)


def machining_feature(op):
    return op.get('depth_mm') is not None and not op.get('reference_only', False) and op['kind'] in ('POCKET', 'HOLE', 'TAPER')


def select_machining_face(part, flip_over=None):
    """Put the face with most machining features at +Z; retain underside metadata."""
    if 'machining_face' in part:
        if flip_over is None or bool(flip_over)==part.get('manual_flip',False):
            return part
        part=part['_unoriented_part']
    flip_over=bool(flip_over)
    features={side:[op for op in part['operations'] if op['side']==side and machining_feature(op)] for side in ('FRONT','BACK')}
    scores={side:(len(ops),sum(op['face'].Area for op in ops),sum(op['depth_mm'] for op in ops)) for side,ops in features.items()}
    chosen='BACK' if scores['BACK']>scores['FRONT'] else 'FRONT'
    if flip_over:chosen='FRONT' if chosen=='BACK' else 'BACK'
    result=dict(part);result['machining_face']=chosen
    result['_unoriented_part']=part;result['manual_flip']=flip_over
    result['face_selection']={'rule':'Most recessed machining features; ties use total recessed area, then total depth.',
                              'original_face_up':chosen,'manually_flipped':flip_over,
                              'scores':{side:{'features':value[0],'recessed_area_mm2':value[1],'total_depth_mm':value[2]} for side,value in scores.items()}}
    shape=part['shape'].copy()
    flip=chosen=='BACK'
    if flip:
        shape.rotate(App.Vector(),App.Vector(0,1,0),180)
        box=shape.optimalBoundingBox();shape.translate(App.Vector(-box.XMin,-box.YMin,-box.ZMin))
    result['shape']=shape;result['operations']=[];result['underside_operations']=[]
    for original in part['operations']:
        op=dict(original);op['original_side']=original['side'];face=original['face'].copy()
        if flip:
            face.rotate(App.Vector(),App.Vector(0,1,0),180)
            face.translate(App.Vector(part['width_mm'],0,0))
        op['face']=flat_face(face)
        through=op['kind'] in ('OUTLINE','CUTOUT') or (op['kind']=='HOLE' and op['depth_mm'] is None)
        # The outline and through-openings belong in the single UP setup,
        # regardless of which face originally held their drawing convention.
        if through or op['side']==chosen:
            op['side']='FRONT'  # Internal convention: +Z machining face.
            result['operations'].append(op)
        else:
            op['side']='BACK';result['underside_operations'].append(op)
    def map_note(text):
        return re.sub(r'\b(FRONT|BACK|front|back)\b(?! land)',lambda m:'UP' if m.group(0).upper()==chosen else 'UNDERSIDE',text)
    result['notes']=[map_note(note) for note in part['notes']]
    result['underside_feature_count']=sum(machining_feature(op) for op in result['underside_operations'])
    if result['underside_feature_count']:
        result['notes'].append('%d underside machining feature(s) are not included in the UP DXF. They remain in the exact 3D part and the underside operations list in manifest.json.'%result['underside_feature_count'])
    return result


def face_label(side):
    return 'UP' if side=='FRONT' else 'UNDERSIDE'


def apply_part_options(part, rotation_deg=0, grain_axis='NONE', rebate_extension_mm=0, flip_over=None):
    part = select_machining_face(part, flip_over)
    if rotation_deg not in (0, 90, 180, 270):
        raise ExportError('Part rotation must be 0, 90, 180 or 270 degrees.')
    if grain_axis not in ('NONE', 'X', 'Y'):
        raise ExportError('Unknown grain direction.')
    if not math.isfinite(rebate_extension_mm) or rebate_extension_mm < 0:
        raise ExportError('Rebate extension must be a finite, non-negative distance.')
    result = dict(part)
    result['notes'] = list(part['notes'])
    result['reference_width_mm'] = part['width_mm']
    result['reference_height_mm'] = part['height_mm']
    result['rotation_deg'] = rotation_deg
    result['grain_axis_before_rotation'] = grain_axis
    result['grain_axis_on_sheet'] = ('Y' if grain_axis == 'X' else 'X') if grain_axis != 'NONE' and rotation_deg in (90, 270) else grain_axis
    result['rebate_extension_mm'] = rebate_extension_mm
    shape = part['shape'].copy()
    shape.rotate(App.Vector(), Z, rotation_deg)
    box = shape.optimalBoundingBox()
    offset = App.Vector(-box.XMin, -box.YMin, 0)
    shape.translate(offset)
    result['shape'] = shape
    result['width_mm'], result['height_mm'] = box.XLength, box.YLength
    operations = []
    for original in part['operations']:
        op = dict(original)
        face = original['face'].copy()
        face.rotate(App.Vector(), Z, rotation_deg)
        face.translate(offset)
        op['face'] = flat_face(face)
        operations.append(op)
    outline = operations[0]['face']
    extension_count = 0
    for op in operations:
        if op['kind'] == 'POCKET' and rebate_extension_mm > TOL:
            try:
                op['face'], count = extend_rebate(op['face'], outline, rebate_extension_mm, shape, op['depth_mm'], op['side'])
            except Exception as exc:
                raise ExportError('%s (%s, extension %s mm): %s' % (op['layer'], op['side'], mm(rebate_extension_mm), exc)) from exc
            op['extended_open_edges'] = count
            op['rebate_extension_mm'] = rebate_extension_mm if count else 0
            extension_count += count
    result['operations'] = operations
    if rebate_extension_mm > TOL:
        result['notes'].append('%d open rebate edge(s) extended by %s mm outside the finished outline.' % (extension_count, mm(rebate_extension_mm)))
    # Reserve all front AND back operations at the same physical placement.
    boxes = [op['face'].optimalBoundingBox() for op in operations]
    result['machining_bounds_mm'] = [min(b.XMin for b in boxes), min(b.YMin for b in boxes),
                                     max(b.XMax for b in boxes), max(b.YMax for b in boxes)]
    result['extended_open_edges'] = extension_count
    return result


def sheet_settings(values=None):
    settings = {'width_mm': 2440.0, 'height_mm': 1220.0, 'margin_mm': 10.0,
                'gap_mm': 10.0, 'grain_axis': 'X', 'extension_mm': 0.0}
    if values:
        settings.update(values)
    for key in ('width_mm', 'height_mm', 'margin_mm', 'gap_mm', 'extension_mm'):
        value = float(settings[key])
        if not math.isfinite(value) or value < 0:
            raise ExportError('Sheet dimensions, margin and spacing must be finite and non-negative.')
        settings[key] = value
    if min(settings['width_mm'], settings['height_mm']) <= 2 * settings['margin_mm'] + TOL:
        raise ExportError('The sheet edge margin leaves no usable area.')
    if settings['grain_axis'] not in ('X', 'Y'):
        raise ExportError('Select grain along sheet length or sheet width.')
    return settings


def thickness_key(value):
    value = float(value)
    if not math.isfinite(value) or value <= TOL:
        raise ExportError('A panel has an invalid detected thickness.')
    # Remove geometric floating-point noise, not real stock differences.
    return mm(round(value, 4))


def stock_profiles(parts, settings=None):
    keys = sorted({thickness_key(p['thickness_mm']) for p in parts}, key=float)
    supplied = settings.get('by_thickness') if settings else None
    profiles = {}
    for key in keys:
        if supplied is not None and key not in supplied:
            raise ExportError('No sheet settings were provided for %s mm material.' % key)
        values = supplied[key] if supplied is not None else settings
        try:
            profiles[key] = sheet_settings(values)
        except Exception as exc:
            raise ExportError('%s mm sheet settings: %s' % (key, exc)) from exc
    return profiles


def expand_quantity(part, quantity, source_row):
    if isinstance(quantity, bool) or not isinstance(quantity, int) or quantity < 0 or quantity > 999:
        raise ExportError('Quantity must be a whole number from 0 to 999.')
    copies = []
    for index in range(1, quantity + 1):
        copy = dict(part)
        copy['source_row'] = source_row
        copy['source_part_label'] = part['label']
        copy['quantity_requested'] = quantity
        copy['copy_number'] = index
        if quantity > 1:
            copy['label'] = '%s_copy_%02d_of_%02d' % (part['label'], index, quantity)
        copies.append(copy)
    return copies


def split_free_rectangles(rectangles, used):
    """MaxRects free-space splitting; orientations are supplied, never guessed."""
    ux, uy, uw, uh = used
    result = []
    for x, y, w, h in rectangles:
        if ux >= x + w - TOL or ux + uw <= x + TOL or uy >= y + h - TOL or uy + uh <= y + TOL:
            result.append((x, y, w, h))
            continue
        if ux > x + TOL:
            result.append((x, y, ux - x, h))
        if ux + uw < x + w - TOL:
            result.append((ux + uw, y, x + w - ux - uw, h))
        if uy > y + TOL:
            result.append((x, y, w, uy - y))
        if uy + uh < y + h - TOL:
            result.append((x, uy + uh, w, y + h - uy - uh))
    pruned = []
    for i, rect in enumerate(result):
        x, y, w, h = rect
        if w <= TOL or h <= TOL:
            continue
        contained = False
        for j, other in enumerate(result):
            if i == j:
                continue
            ox, oy, ow, oh = other
            if x >= ox - TOL and y >= oy - TOL and x + w <= ox + ow + TOL and y + h <= oy + oh + TOL:
                # Keep one representative when two free rectangles are equal.
                equal = all(abs(a - b) < TOL for a, b in zip(rect, other))
                if not equal or j < i:
                    contained = True
                    break
        if not contained:
            pruned.append(rect)
    return pruned


def pack_sheets(parts, settings):
    profiles = stock_profiles(parts, settings)
    sheets = []
    indexed = list(enumerate(parts, 1))
    # Largest rectangles first; this is practical rectangular packing, not an
    # optimal material-yield claim or interlocking irregular-shape nesting.
    indexed.sort(key=lambda pair: -(pair[1]['machining_bounds_mm'][2] - pair[1]['machining_bounds_mm'][0]) *
                                  (pair[1]['machining_bounds_mm'][3] - pair[1]['machining_bounds_mm'][1]))
    for index, part in indexed:
        key = thickness_key(part['thickness_mm'])
        profile = profiles[key]
        margin, gap = profile['margin_mm'], profile['gap_mm']
        width, height = profile['width_mm'], profile['height_mm']
        usable_w, usable_h = width - 2 * margin, height - 2 * margin
        if part['grain_axis_on_sheet'] not in ('NONE', profile['grain_axis']):
            raise ExportError('%s: grain conflicts with the sheet. Rotate the part by 90 degrees, change its reference grain axis, or change the sheet grain setting.' % part['label'])
        x0, y0, x1, y1 = part['machining_bounds_mm']
        pw, ph = x1 - x0, y1 - y0
        if pw > usable_w + TOL or ph > usable_h + TOL:
            raise ExportError('%s needs %s × %s mm including rebate extensions and will not fit the usable %s × %s mm sheet at %d°. Change its rotation, sheet size or margin.' %
                              (part['label'], mm(pw), mm(ph), mm(usable_w), mm(usable_h), part['rotation_deg']))
        rw, rh = pw + gap, ph + gap
        fits = []
        for sheet in sheets:
            if sheet['thickness_key'] != key:
                continue
            for fx, fy, fw, fh in sheet['_free']:
                if rw <= fw + TOL and rh <= fh + TOL:
                    fits.append((min(fw - rw, fh - rh), max(fw - rw, fh - rh), sheet['index'], fy, fx, sheet))
        if fits:
            _, _, _, fy, fx, sheet = min(fits, key=lambda f: f[:5])
        else:
            sheet = {'index': len(sheets) + 1, 'width_mm': width, 'height_mm': height,
                     'thickness_mm': float(key), 'thickness_key': key, 'stock_settings': dict(profile), 'placements': [],
                     '_free': [(margin, margin, usable_w + gap, usable_h + gap)]}
            sheets.append(sheet)
            fx, fy = margin, margin
        sheet['placements'].append({'part_index': index, 'part': part,
                                    'x_mm': fx - x0, 'y_mm': fy - y0,
                                    'bounds_mm': [fx, fy, fx + pw, fy + ph]})
        sheet['_free'] = split_free_rectangles(sheet['_free'], (fx, fy, rw, rh))
    # Independent placement guard on every export, including expanded pockets.
    for sheet in sheets:
        profile = sheet['stock_settings']
        width, height = sheet['width_mm'], sheet['height_mm']
        margin, gap = profile['margin_mm'], profile['gap_mm']
        for i, placement in enumerate(sheet['placements']):
            a = placement['bounds_mm']
            if a[0] < margin - TOL or a[1] < margin - TOL or a[2] > width - margin + TOL or a[3] > height - margin + TOL:
                raise ExportError('Internal layout error: machining geometry crossed the sheet margin.')
            for other in sheet['placements'][:i]:
                b = other['bounds_mm']
                separated = a[2] + gap <= b[0] + TOL or b[2] + gap <= a[0] + TOL or a[3] + gap <= b[1] + TOL or b[3] + gap <= a[1] + TOL
                if not separated:
                    raise ExportError('Internal layout error: two machining envelopes overlap or lack the requested spacing.')
        sheet['has_back'] = any(op['side'] == 'BACK' for p in sheet['placements'] for op in p['part']['operations'])
        sheet.pop('_free', None)
    if not sheets:
        raise ExportError('No parts were selected.')
    return sheets


def placed_wire(wire, placement, sheet, side):
    copy = wire.copy()
    copy.translate(App.Vector(placement['x_mm'], placement['y_mm'], 0))
    if side == 'BACK':
        copy.rotate(App.Vector(), App.Vector(0, 1, 0), 180)
        copy.translate(App.Vector(sheet['width_mm'], 0, 0))
    return copy


def grain_segments(x, y, width, height, axis):
    if axis == 'NONE':
        return []
    cx, cy = x + width / 2, y + height / 2
    length = min(width, height) * 0.22
    head = min(8, length / 4)
    if axis == 'X':
        a, b = (cx - length / 2, cy), (cx + length / 2, cy)
        return [(a, b), (b, (b[0] - head, b[1] + head / 2)), (b, (b[0] - head, b[1] - head / 2))]
    a, b = (cx, cy - length / 2), (cx, cy + length / 2)
    return [(a, b), (b, (b[0] + head / 2, b[1] - head)), (b, (b[0] - head / 2, b[1] - head))]


def sheet_drawing(sheet, side, settings, palette=None):
    settings = sheet['stock_settings']
    if palette is None:
        palette = palette_for_parts([p['part'] for p in sheet['placements']])
    drawing = Dxf(palette)
    drawing.add_wire(rectangle_wire(sheet['width_mm'], sheet['height_mm']), 'REFERENCE_SHEET')
    margin = settings['margin_mm']
    if margin > TOL:
        drawing.add_wire(rectangle_wire(sheet['width_mm'] - 2 * margin, sheet['height_mm'] - 2 * margin, margin, margin), 'REFERENCE_MARGIN')
    for placement in sheet['placements']:
        part = placement['part']
        for op in face_operations(part, side):
            for wire in op['face'].Wires:
                drawing.add_wire(placed_wire(wire, placement, sheet, side), op['layer'])
        x = placement['x_mm'] if side == 'FRONT' else sheet['width_mm'] - placement['x_mm'] - part['width_mm']
        y = placement['y_mm']
        drawing.add_text('%02d %s' % (placement['part_index'], part['label']), x + 3, y + 3, min(5, part['height_mm'] / 8))
        for note_index,note in enumerate(cut_annotations(part,side)):
            drawing.add_text(note,x+3,y+part['height_mm']/2+note_index*6,4)
        for a, b in grain_segments(x, y, part['width_mm'], part['height_mm'], part['grain_axis_on_sheet']):
            drawing.add_line(a, b)
    drawing.add_text('SHEET %02d | %s | %s mm | STOCK GRAIN %s | reference layers are not cuts' %
                     (sheet['index'], face_label(side), mm(sheet['thickness_mm']), settings['grain_axis']), 0, -18, 7)
    return drawing


def output_parts(parts, parent, title='FreeCAD_Lay_Flat_for_CNC', create_preview=True, settings=None, drawing_formats=('dxf',), expected_layout=None):
    """Write individual DXFs and bounded sheet DXFs into a fresh directory."""
    # Preserve the callable API for callers supplying unconfigured analysed parts.
    drawing_formats = sheet_runtime().validate_formats(drawing_formats)
    parts = [p if 'machining_bounds_mm' in p else apply_part_options(p) for p in parts]
    settings = {'by_thickness': stock_profiles(parts, settings)}
    sheets = pack_sheets(parts, settings)
    if expected_layout is not None:
        placements = [[{k:v for k,v in p.items() if k != 'part'} for p in sheet['placements']] for sheet in sheets]
        if placements != [sheet['placements'] for sheet in expected_layout]:
            raise ExportError('The saved layout cannot be reproduced exactly; export the sheet drawings only.')
    palette = palette_for_parts(parts)
    parent = Path(parent)
    if not parent.is_dir():
        raise ExportError('Choose an existing output folder.')
    final_name = '%s_sheets_%s' % (safe_name(title), datetime.now().strftime('%Y%m%d_%H%M%S_%f'))
    staging = Path(tempfile.mkdtemp(prefix='.freecad-lay-flat-', dir=str(parent)))
    manifest = {'exporter_version': VERSION, 'units': 'mm', 'title': title,
                'depth_datum': 'UP operation depths are measured from the original upward stock surface. Reported underside depths are measured from the opposite stock surface.',
                'machining_face': 'Each panel is oriented with its most recessed machining features UP. Only this setup is drawn; underside features are reported separately.',
                'underside_geometry': 'Exact STEP and FCStd solids retain both sides. No separate underside DXF or sheet layout is generated.',
                'layout': 'Fixed-orientation rectangular packing of all machining envelopes, including rebate extensions. Reference and label layers are not toolpaths.',
                'stock_settings': settings, 'drawing_formats': list(drawing_formats), 'dxf_version': 'R12' if 'dxf_r12' in drawing_formats and 'dxf' not in drawing_formats else 'R2004', 'layer_colours': palette, 'parts': [], 'sheets': []}
    if 'dxf_r12' in drawing_formats:
        manifest['mozaik_import_verified'] = False
        manifest['r12_layer_names'] = sheet_runtime().r12_layer_names(palette)
    placements_by_index = {p['part_index']: (s, p) for s in sheets for p in s['placements']}
    try:
        for index, part in enumerate(parts, 1):
            part_id = '%02d_%s' % (index, safe_name(part['label']))
            record = {k: part[k] for k in ['label', 'width_mm', 'height_mm', 'thickness_mm', 'notes', 'verification',
                       'rotation_deg', 'reference_width_mm', 'reference_height_mm', 'grain_axis_before_rotation',
                       'grain_axis_on_sheet', 'rebate_extension_mm', 'machining_bounds_mm', 'extended_open_edges']}
            record['id'], record['files'] = part_id, []
            step_name=part_id+'.step'
            part['shape'].exportStep(str(staging / step_name))
            record['step_file']=step_name
            record['source_row'] = part.get('source_row', index)
            record['source_part_label'] = part.get('source_part_label', part['label'])
            record['quantity_requested'] = part.get('quantity_requested', 1)
            record['copy_number'] = part.get('copy_number', 1)
            record['source_instance'] = part.get('source_instance', '')
            record['source_document'] = part.get('source_document', '')
            record['source_object'] = part.get('source_object', '')
            record['fillet_removal'] = part.get('fillet_removal', {'status': 'disabled', 'maximum_radius_mm': 0})
            record['verification_scope'] = 'Prismatic and ruled-taper operations are reconstructed; remaining finishing removal is confined to identified convex roundover envelopes. STEP and flat FCStd files retain the export geometry, including any explicitly requested fillet removal recorded here. Rebate extensions are separately checked against that solid.'
            record['operations'] = [{**{k: v for k, v in op.items() if k != 'face'}, 'side': 'UP'} for op in part['operations']]
            record['face_selection']=part['face_selection']
            record['underside_feature_count']=part['underside_feature_count']
            record['underside_operations']=[{**{k:v for k,v in op.items() if k!='face'}, 'side':'UNDERSIDE'} for op in part['underside_operations']]
            sheet, placement = placements_by_index[index]
            record['layer_groups'] = [{'face': face_label(side), 'layer': layer, 'feature_count': len(ops)}
                for side in ('FRONT', 'BACK') for layer, ops in grouped_face_operations(part, side)
                if side == 'FRONT' or any(op['side'] == 'BACK' for op in part['operations'])]
            record['sheet'] = sheet['index']
            record['sheet_origin_mm'] = [placement['x_mm'], placement['y_mm']]
            sides = ['FRONT'] + (['BACK'] if any(op['side'] == 'BACK' for op in part['operations']) else [])
            for side in sides:
                drawing = Dxf(palette)
                mirror = part['width_mm'] if side == 'BACK' else None
                for op in face_operations(part, side):
                    for wire in op['face'].Wires:
                        drawing.add_wire(wire, op['layer'], mirror_width=mirror)
                for a, b in grain_segments(0, 0, part['width_mm'], part['height_mm'], part['grain_axis_on_sheet']):
                    drawing.add_line(a, b)
                drawing.add_text('%s | %s | %s mm | %d deg' % (part_id, face_label(side), mm(part['thickness_mm']), part['rotation_deg']),
                                 0, part['machining_bounds_mm'][1] - 12)
                for note_index, note in enumerate(cut_annotations(part, side)):
                    drawing.add_text(note, 3, part['height_mm']/2 + note_index*6, 4)
                record['files'].extend(sheet_runtime().write_drawing(drawing, staging, part_id+'_'+face_label(side),
                    drawing_formats, part['width_mm'], part['height_mm'], bounds=part['machining_bounds_mm']))
            manifest['parts'].append(record)
        for sheet in sheets:
            record = {k: sheet[k] for k in ('index', 'width_mm', 'height_mm', 'thickness_mm', 'has_back', 'stock_settings')}
            record['placements'] = [{k: v for k, v in p.items() if k != 'part'} for p in sheet['placements']]
            record['files'] = []
            for side in ['FRONT'] + (['BACK'] if sheet['has_back'] else []):
                basename = 'Sheet_%02d_%sMM_%s' % (sheet['index'], token(sheet['thickness_mm']), face_label(side))
                record['files'].extend(sheet_runtime().write_drawing(sheet_drawing(sheet, side, settings, palette),
                    staging, basename, drawing_formats, sheet['width_mm'], sheet['height_mm']))
            manifest['sheets'].append(record)
        with open(staging / 'parts.csv', 'w', newline='', encoding='utf-8-sig') as stream:
            writer = csv.writer(stream)
            writer.writerow(['Part', 'Label', 'Width_mm', 'Height_mm', 'Thickness_mm', 'Rotation_deg', 'Grain_axis_on_sheet',
                             'Rebate_extension_mm', 'Sheet', 'Sheet_X_mm', 'Sheet_Y_mm', 'Drawing_files',
                             'Source_row', 'Copy_number', 'Row_quantity', 'Assembly_instance'])
            for r in manifest['parts']:
                writer.writerow([r['id'], r['label'], mm(r['width_mm']), mm(r['height_mm']), mm(r['thickness_mm']), r['rotation_deg'],
                                 r['grain_axis_on_sheet'], mm(r['rebate_extension_mm']), r['sheet'],
                                 mm(r['sheet_origin_mm'][0]), mm(r['sheet_origin_mm'][1]), '; '.join(r['files']),
                                 r['source_row'], r['copy_number'], r['quantity_requested'], r['source_instance']])
        quantities = {}
        for r in manifest['parts']:
            quantities.setdefault(r['source_row'], {'source_row': r['source_row'],
                'label': r['source_part_label'], 'quantity': r['quantity_requested'],
                'thickness_mm': r['thickness_mm'], 'source_instance': r['source_instance']})
        manifest['quantities'] = list(quantities.values())
        with open(staging / 'quantities.csv', 'w', newline='', encoding='utf-8-sig') as stream:
            writer = csv.writer(stream)
            writer.writerow(['Source_row', 'Part', 'Quantity', 'Thickness_mm', 'Assembly_instance'])
            for q in manifest['quantities']:
                writer.writerow([q['source_row'], q['label'], q['quantity'], mm(q['thickness_mm']), q['source_instance']])
        (staging / 'SHEET_NOTES.txt').write_text(
            'Use the Sheet_*.dxf or Sheet_*.svg files for the sheet layout. All dimensions are millimetres. SVG page dimensions are 1:1.\n'
            'REFERENCE_SHEET, REFERENCE_MARGIN, REFERENCE_GRAIN, REFERENCE_OUTLINE and LABELS are not cutting operations.\n'
            'Each panel has its most complex machining face UP. Only one UP layout is exported per sheet.\n'
            'Any underside operations are listed in manifest.json and part notes; exact 3D files retain them.\n'
            'Rebate exits extend straight; a shallow cut may pass through an existing deeper cut. The finished solid must remain unchanged.\n'
            'Sheet spacing is measured between UP machining boundaries, including these extensions. Set spacing and margin for your tooling.\n'
            'Grain is supplied by the user; it is not inferred from the model. Unspecified grain still uses the chosen fixed rotation.\n'
            'Different thicknesses have independent sheet settings and never share a sheet. Same-thickness parts are assumed to use the same material.\n'
            'Quantities are total copies per source row; assembly instances are preserved separately. See quantities.csv.\n'
            'All depths are measured from the original board face. TIP distinguishes drill-tip depth from full-diameter depth.\n'
            'Operation layer names and colours are user-editable; original identifiers and exact depths remain in manifest.json.\n'
            'Standard DXF uses R2004/RGB colours. The Mozaik preset uses R12 closed polylines and indexed colours, omitting guides and labels. Choose millimetres on import.\n'
            'For Mozaik part import, use individual-part *_R12.dxf files, not nested Sheet_* drawings. Assign tools inside Mozaik; actual Mozaik import is unverified. R12 layer aliases are listed in manifest.json.\n'
            'Flat_parts.FCStd and individual STEP files use the export geometry, including requested fillet removal. The source model is unchanged.\n'
            'Fillet removal includes the selected radius. It uses native PartDesign fillet history, never the radius of arbitrary arcs or holes. See each part\'s fillet_removal record in manifest.json.\n'
            'STEP/imported solids without native fillet history keep their fillets. A cutoff of 0 disables removal.\n'
            'TAPER layers give wide and narrow contours with angle and start/end depths from the named board face. These are geometry for CAM setup, not cutter-compensated toolpaths.\n'
            'REFERENCE_TAPER and REFERENCE_EDGE_ROUND layers are guides, not through cuts. Rounded finishing regions are envelopes; use the exact STEP surface for cutter setup.\n'
            'Parts were manually selected. Panel tags are selection defaults; names, STEP origin and thickness never exclude solid parts. Thickness is measured from geometry.\n', encoding='utf-8')
        if 'dxf_r12' in drawing_formats:sheet_runtime().write_r12_layer_guide(staging, palette)
        save_flat_solids(sheets, staging / 'Flat_parts.FCStd')
        manifest['flat_parts_file']='Flat_parts.FCStd'
        manifest['preview'] = {'requested': bool(create_preview), 'created': False}
        if create_preview:
            preview_path = staging / 'Sheet_layout.FCStd'
            try:
                save_sheet_preview(sheets, settings, preview_path, palette, title=title)
                manifest['preview'].update({'created': True, 'file': preview_path.name})
            except Exception as exc:
                # DXF generation succeeded: report an optional preview failure
                # separately instead of discarding the user's valid exports.
                manifest['preview']['error'] = str(exc)
                App.Console.PrintWarning('Lay Flat for CNC DXFs created, but the FreeCAD preview failed: %s\n' % exc)
                if preview_path.exists():
                    preview_path.unlink()
        (staging / 'manifest.json').write_text(json.dumps(manifest, indent=2), encoding='utf-8')
        destination = parent / final_name
        staging.rename(destination)
        return destination, manifest
    except Exception:
        import shutil
        shutil.rmtree(staging, ignore_errors=True)
        raise


def operation_description(op):
    """Human-readable machining meaning, independent of object numbering."""
    kind = op['kind']
    depth = 'through' if op.get('depth_mm') is None else 'depth %s mm' % mm(op['depth_mm'])
    if op['layer'] == 'REFERENCE_OUTLINE':
        text = 'Part outlines — guide only'
    elif kind == 'OUTLINE':
        text = 'Outside profiles — through'
    elif kind == 'CUTOUT':
        text = 'Internal cutouts — through'
    elif kind == 'HOLE':
        text = 'Holes — diameter %s mm — %s' % (mm(op['diameter_mm']), depth)
        if op.get('tip_depth_mm') is not None:
            text += ' — drill tip depth %s mm' % mm(op['tip_depth_mm'])
    elif kind == 'POCKET':
        text = 'Pockets — ' + depth
    elif kind == 'TAPER':
        text = 'Taper — %s° — %s contour — depth %s to %s mm' % (
            mm(op['angle_deg']), op['contour'], mm(op['start_depth_mm']), mm(op['end_depth_mm']))
    elif kind == 'EDGE_ROUND':
        text = 'Roundover — radius %s mm' % mm(op['radius_mm'])
    else:
        text = op['layer']
    if op.get('reference_only'):
        text += ' — guide only'
    if op.get('source_layer', op['layer']) != op['layer'] and op['layer'] != 'REFERENCE_OUTLINE':
        text = op['layer'] + ' — ' + text
    return text


def grouped_sheet_operations(sheet, side):
    """One layer object per sheet/setup, with complete part provenance."""
    groups = {}
    for placement in sheet['placements']:
        for op in face_operations(placement['part'], side):
            group = groups.setdefault(op['layer'], {'layer': op['layer'], 'operation': op,
                'wires': [], 'feature_count': 0, 'parts': {}})
            group['wires'].extend(placed_wire(wire, placement, sheet, side) for wire in op['face'].Wires)
            group['feature_count'] += 1
            group['parts'][placement['part_index']] = placement['part']['label']
    ranks = {'OUTLINE': 0, 'CUTOUT': 1, 'POCKET': 2, 'HOLE': 3, 'TAPER': 4}
    return sorted(groups.values(), key=lambda group: (
        ranks.get(group['operation']['kind'], 5),
        group['operation'].get('depth_mm') or 0,
        group['operation'].get('diameter_mm') or 0, group['layer']))


def add_sheet_operation(doc, parent, operation_group, context, offset_y, palette):
    layer = operation_group['layer']
    op = operation_group['operation']
    obj = doc.addObject('Part::Feature', 'OperationLayer')
    description = operation_description(op)
    obj.Label = '%s (%s)' % (description, context)
    obj.addProperty('App::PropertyString', 'DxfLayer', 'Export').DxfLayer = layer
    obj.addProperty('App::PropertyString', 'Operation', 'Export').Operation = description
    obj.addProperty('App::PropertyInteger', 'FeatureCount', 'Export').FeatureCount = operation_group['feature_count']
    obj.addProperty('App::PropertyInteger', 'PartCount', 'Export').PartCount = len(operation_group['parts'])
    obj.addProperty('App::PropertyStringList', 'PartNumbers', 'Export').PartNumbers = [str(i) for i in sorted(operation_group['parts'])]
    obj.addProperty('App::PropertyStringList', 'PartLabels', 'Export').PartLabels = [operation_group['parts'][i] for i in sorted(operation_group['parts'])]
    obj.addProperty('App::PropertyInteger', 'WireCount', 'Export').WireCount = len(operation_group['wires'])
    shape = Part.makeCompound(operation_group['wires'])
    shape.translate(App.Vector(0, offset_y, 0))
    obj.Shape = shape
    parent.addObject(obj)
    if App.GuiUp:
        obj.ViewObject.LineColor = layer_rgb(palette, layer)
        obj.ViewObject.LineWidth = 2.0
        obj.ViewObject.DisplayMode = 'Wireframe'
        obj.ViewObject.Visibility = True
    return obj


def save_sheet_preview(sheets, settings, path=None, palette=None, title='Sheet layout'):
    if palette is None:
        palette = palette_for_parts([p['part'] for sheet in sheets for p in sheet['placements']])
    previous = App.ActiveDocument
    doc = App.newDocument('Sheet_layout')
    completed = False
    try:
        doc.Label = 'Sheet layout'
        marker = doc.addObject('App::FeaturePython', 'FreeCADLayFlatSheetExportMarker')
        marker.Label = 'Export preview — use the original model for new exports'
        drawings = doc.addObject('App::DocumentObjectGroupPython', 'SheetLayouts')
        drawings.Label = 'Sheet layouts — operations'
        reference_solids = doc.addObject('App::DocumentObjectGroup', 'ReferenceSolids')
        reference_solids.Label = '3D copies — reference only'
        solid_objects = []
        sheet_objects = []
        offset_y = 0.0
        for sheet in sheets:
            sheet_profile = sheet['stock_settings']
            solid_group = doc.addObject('App::DocumentObjectGroup', 'SheetSolidCopies')
            solid_group.Label = 'Sheet %02d — 3D copies' % sheet['index']
            reference_solids.addObject(solid_group)
            for side in ['FRONT'] + (['BACK'] if sheet['has_back'] else []):
                group = doc.addObject('App::DocumentObjectGroupPython', 'Sheet')
                group.Label = 'Sheet %02d — %s — %s mm' % (sheet['index'], face_label(side), mm(sheet['thickness_mm']))
                drawings.addObject(group)
                if side == 'FRONT':sheet_objects.append(group)
                context = 'Sheet %d%s' % (sheet['index'], ' underside' if side == 'BACK' else '')
                guides = doc.addObject('App::DocumentObjectGroup', 'SheetGuides')
                guides.Label = 'Guides — not cuts (%s)' % context
                labels = doc.addObject('App::DocumentObjectGroup', 'SheetPartLabels')
                labels.Label = 'Part labels (%s)' % context
                guides.addObject(labels)
                # Operation items appear first; reference geometry is kept separate.
                for operation_group in grouped_sheet_operations(sheet, side):
                    op = operation_group['operation']
                    parent = guides if op.get('reference_only') or operation_group['layer'].startswith('REFERENCE_') else group
                    add_sheet_operation(doc, parent, operation_group, context, offset_y, palette)
                group.addObject(guides)
                boundary = doc.addObject('Part::Feature', 'SheetBoundary')
                boundary.Label = 'Sheet boundary (%s)' % context
                boundary.Shape = rectangle_wire(sheet['width_mm'], sheet['height_mm'], 0, offset_y)
                guides.addObject(boundary)
                if App.GuiUp:
                    boundary.ViewObject.LineColor = layer_rgb(palette, 'REFERENCE_SHEET')
                margin = sheet_profile['margin_mm']
                if margin > TOL:
                    obj = doc.addObject('Part::Feature', 'SheetMargin')
                    obj.Label = 'Edge margin (%s)' % context
                    obj.Shape = rectangle_wire(sheet['width_mm'] - 2 * margin, sheet['height_mm'] - 2 * margin, margin, offset_y + margin)
                    guides.addObject(obj)
                    if App.GuiUp:
                        obj.ViewObject.LineColor = layer_rgb(palette, 'REFERENCE_MARGIN')
                grain_wires = []
                for placement in sheet['placements']:
                    part = placement['part']
                    x = placement['x_mm'] if side == 'FRONT' else sheet['width_mm'] - placement['x_mm'] - part['width_mm']
                    y = placement['y_mm'] + offset_y
                    segments = grain_segments(x, y, part['width_mm'], part['height_mm'], part['grain_axis_on_sheet'])
                    grain_wires.extend(Part.makeLine(App.Vector(a[0], a[1], 0), App.Vector(b[0], b[1], 0)) for a, b in segments)
                    if side == 'FRONT':
                        obj = doc.addObject('Part::Feature', 'FlatPanel')
                        obj.Label = 'Part %02d — 3D reference (%s)' % (placement['part_index'], context)
                        obj.addProperty('App::PropertyString', 'PartDescription', 'Export').PartDescription = part['label']
                        copy = part['shape'].copy()
                        # The reference solid is entirely below the Z=0 drawing
                        # plane. Even Show All cannot put it over the DXF lines
                        # in the default top view. Actual DXF geometry is unchanged.
                        preview_z = -copy.BoundBox.ZMax - 0.2
                        copy.translate(App.Vector(placement['x_mm'], placement['y_mm'] + offset_y, preview_z))
                        obj.Shape = copy
                        solid_group.addObject(obj)
                        solid_objects.append(obj)
                        obj.addProperty('App::PropertyString', 'PreviewNote', 'Export').PreviewNote = 'Display-only copy below the DXF drawing plane; not exported as cutting geometry.'
                        if App.GuiUp:
                            obj.ViewObject.ShapeColor = (0.85, 0.85, 0.85)
                            obj.ViewObject.DisplayMode = 'Flat Lines'
                            obj.ViewObject.Visibility = False
                    if App.GuiUp:
                        label = doc.addObject('App::Annotation', 'PartLabel')
                        label.Label = 'Part %02d (%s)' % (placement['part_index'], context)
                        label.LabelText = ['%02d' % placement['part_index']]
                        label.addProperty('App::PropertyString', 'PartDescription', 'Export').PartDescription = part['label']
                        label.Position = App.Vector(x + 3, y + 3, 0)
                        label.ViewObject.FontSize = 5
                        labels.addObject(label)
                if grain_wires:
                    obj = doc.addObject('Part::Feature', 'GrainDirection')
                    obj.Label = 'Grain direction (%s)' % context
                    obj.Shape = Part.makeCompound(grain_wires)
                    guides.addObject(obj)
                    if App.GuiUp:
                        obj.ViewObject.LineColor = layer_rgb(palette, 'REFERENCE_GRAIN')
                if App.GuiUp:
                    label = doc.addObject('App::Annotation', 'SheetLabel')
                    label.Label = 'Sheet title (%s)' % context
                    label.LabelText = [group.Label + ' — stock grain ' + sheet_profile['grain_axis']]
                    label.Position = App.Vector(0, offset_y - 20, 0)
                    label.ViewObject.FontSize = 10
                    guides.addObject(label)
                offset_y += sheet['height_mm'] + 150
        sheet_runtime().bind_layout(doc, drawings, sheet_objects, sheets, settings, palette, globals(), title)
        doc.recompute()
        if App.GuiUp:
            import FreeCADGui as Gui
            # Apply visibility after constructing the group tree: the drawing
            # hierarchy contains no solids for group show/hide to reveal.
            drawings.ViewObject.Visibility = True
            reference_solids.ViewObject.Visibility = False
            for obj in solid_objects:
                obj.ViewObject.Visibility = False
            Gui.activeDocument().activeView().viewTop()
            Gui.activeDocument().activeView().fitAll()
        if path is not None:doc.saveAs(str(path))
        completed = True
        return doc if path is None else None
    finally:
        if path is not None or not completed:
            App.closeDocument(doc.Name)
            if previous is not None:App.setActiveDocument(previous.Name)


def object_id(obj):
    return (obj.Document.Name, obj.Name)


def is_link_object(obj):
    return obj.isDerivedFrom('App::Link') or obj.TypeId == 'App::LinkElement' or obj.isDerivedFrom('Assembly::AssemblyLink')


def linked_target(obj):
    current, seen = obj, set()
    while is_link_object(current):
        identity = object_id(current)
        if identity in seen:
            raise ExportError('%s contains a circular component link.' % obj.Label)
        seen.add(identity)
        if int(getattr(current, 'ElementCount', 0)) > 0:
            raise ExportError('%s is a linked array. Expand it to individual component links before exporting; array quantities are not inferred.' % current.Label)
        # Native AssemblyLink has an explicit LinkedObject property; ordinary
        # App::Link resolves its current linked definition through its API.
        if current.isDerivedFrom('Assembly::AssemblyLink'):
            target = current.LinkedObject
        else:
            target = current.getLinkedObject() if hasattr(current, 'getLinkedObject') else getattr(current, 'LinkedObject', None)
        if isinstance(target, tuple):
            raise ExportError('%s links to a sub-element rather than a complete component.' % current.Label)
        if target is None or target is current:
            raise ExportError('%s has an unresolved component link. Load its source document first.' % current.Label)
        current = target
    return current


def is_container_object(obj):
    if obj.TypeId == 'PartDesign::Body':
        return False  # A Body is a finished manufactured object, not its history.
    return (obj.TypeId == 'App::LinkGroup' or obj.isDerivedFrom('App::Part') or obj.isDerivedFrom('App::DocumentObjectGroup')
            or obj.isDerivedFrom('Assembly::AssemblyObject') or obj.isDerivedFrom('Assembly::AssemblyLink'))


def is_construction_object(obj):
    kind = obj.TypeId
    return (kind.startswith(('Sketcher::', 'Assembly::Joint', 'App::Origin', 'App::Datum'))
            or kind in ('App::LocalCoordinateSystem', 'PartDesign::Plane', 'PartDesign::Line',
                        'PartDesign::Point', 'PartDesign::CoordinateSystem'))


def default_candidates(doc):
    # Use the document's ownership tree, not every feature or hidden prototype.
    # A source Body referenced by several links must not become another copy.
    if App.GuiUp:
        import FreeCADGui as Gui
        roots = list(Gui.getDocument(doc.Name).TreeRootObjects)
    else:
        roots = list(doc.RootObjects)
    visible = [o for o in roots if not App.GuiUp or o.ViewObject.Visibility]
    assemblies = []
    for obj in visible:
        if is_construction_object(obj):
            continue
        target = linked_target(obj)
        if target.isDerivedFrom('Assembly::AssemblyObject') or obj.isDerivedFrom('Assembly::AssemblyLink'):
            assemblies.append(obj)
    if assemblies:
        return assemblies
    return [o for o in visible if not is_construction_object(o)
            and (is_container_object(o) or is_link_object(o) or hasattr(o, 'Shape') or hasattr(o, 'Mesh'))]


def assembly_seeds(doc, selection):
    seeds = []
    if not selection:
        return [(obj, '', obj, None) for obj in default_candidates(doc)]
    for item in selection:
        root = item.Object
        # Selecting Pad/Pocket history inside a Body means its finished Body.
        if root.TypeId != 'PartDesign::Body' and not is_link_object(root) and hasattr(root, 'getParentGeoFeatureGroup'):
            parent = root.getParentGeoFeatureGroup()
            if parent is not None and parent.TypeId == 'PartDesign::Body':
                root = parent
        normal = next((face.normalAt(0, 0) for face in item.SubObjects
                       if isinstance(face, Part.Face) and isinstance(face.Surface, Part.Plane)), None)
        paths = list(item.SubElementNames) or ['']
        if root.TypeId == 'PartDesign::Body' or linked_target(root).TypeId == 'PartDesign::Body':
            paths = ['']
        for selected_path in paths:
            tokens = [token for token in selected_path.split('.') if token]
            if tokens and re.fullmatch(r'(?:Face|Edge|Vertex)\d+', tokens[-1]):
                tokens.pop()
            path, node = '', root
            for token in tokens:
                path += token + '.'
                try:
                    _shape, _matrix, node = Part.getShape(root, path, retType=1)
                except Exception as exc:
                    raise ExportError('Cannot resolve selected component %s.%s: %s' % (root.Label, path, exc)) from exc
                if node is None:
                    raise ExportError('The selected component %s.%s is unavailable.' % (root.Label, path))
                if linked_target(node).TypeId == 'PartDesign::Body':
                    break
            seeds.append((root, path, node, normal))
    # Remove duplicate or overlapping selections, but never deduplicate links
    # simply because they reference the same source definition.
    unique = {}
    for seed in seeds:
        unique.setdefault((object_id(seed[0]), seed[1]), seed)
    seeds = list(unique.values())

    def owns(parent, child, seen=None):
        if object_id(parent) == object_id(child):
            return True
        if is_link_object(parent) or not hasattr(parent, 'Group'):
            return False
        seen = set() if seen is None else seen
        if object_id(parent) in seen:
            return False
        seen.add(object_id(parent))
        return any(owns(obj, child, seen) for obj in parent.Group)

    result = []
    for seed in seeds:
        root, path, node, _normal = seed
        covered = False
        for other in seeds:
            if other is seed:
                continue
            oroot, opath, onode, _ = other
            if object_id(root) == object_id(oroot) and path != opath and path.startswith(opath):
                covered = True
            elif object_id(root) != object_id(oroot) and not path and owns(onode, root):
                covered = True
        if not covered:
            result.append(seed)
    return result


def is_tagged_panel(node, target=None):
    """An explicit instance tag overrides the linked definition, including False."""
    if PANEL_TAG in node.PropertiesList:
        if node.getTypeIdOfProperty(PANEL_TAG) != 'App::PropertyBool':
            raise ExportError('%s already has an incompatible %s property.' % (node.Label, PANEL_TAG))
        return bool(getattr(node, PANEL_TAG))
    target = target or linked_target(node)
    if target is not node and PANEL_TAG in target.PropertiesList:
        if target.getTypeIdOfProperty(PANEL_TAG) != 'App::PropertyBool':
            raise ExportError('%s already has an incompatible %s property.' % (target.Label, PANEL_TAG))
        return bool(getattr(target, PANEL_TAG))
    return False


def panel_tag_candidates(doc, selection):
    """Expand selected units to individual components, never tag containers."""
    if not selection:
        raise ExportError('Select one or more parts, shelves or cabinets first.')
    skipped = []
    candidates = collect_manufacturing_parts(doc, selection, skipped)
    result, by_object = [], {}
    for candidate in candidates:
        obj = candidate['tag_object']
        identity = object_id(obj)
        if identity in by_object:
            by_object[identity]['solid_occurrences'] += 1
            continue
        row = dict(candidate)
        row['solid_occurrences'] = 1
        row['taggable'] = obj.Document == doc
        by_object[identity] = row
        result.append(row)
    if not any(row['taggable'] for row in result):
        raise ExportError('These components belong to an external source model. Open that model to tag its parts; external files are not edited automatically.')
    return result, skipped


def selected_panel_objects(doc, selection):
    candidates, skipped = panel_tag_candidates(doc, selection)
    return [candidate['tag_object'] for candidate in candidates if candidate['taggable']]


def set_panel_tag_choices(doc, choices):
    """Save mixed tag/untag choices as one metadata-only Undo step."""
    decisions = {}
    for obj, tagged in choices:
        if obj.Document != doc:
            raise ExportError('All tagged parts must belong to the active document.')
        if not isinstance(tagged, bool):
            raise ExportError('Panel tag values must be checked or unchecked.')
        identity = object_id(obj)
        if identity in decisions and decisions[identity][1] != tagged:
            raise ExportError('Conflicting tag choices for ' + obj.Label)
        is_tagged_panel(obj)
        decisions[identity] = (obj, tagged)
    changed = [(obj, tagged) for obj, tagged in decisions.values() if is_tagged_panel(obj) != tagged]
    if not changed:return 0
    if App.getActiveTransaction():
        raise ExportError('Finish the current FreeCAD edit before changing panel tags.')
    if not doc.UndoMode:doc.UndoMode = 1
    doc.openTransaction('Update panel tags')
    try:
        for obj, tagged in changed:
            if PANEL_TAG not in obj.PropertiesList:
                obj.addProperty('App::PropertyBool', PANEL_TAG, 'Lay Flat',
                                'Preselect this component in Lay Flat. False overrides a tag on a linked source. Geometry is unchanged.')
            setattr(obj, PANEL_TAG, tagged)
        doc.commitTransaction()
    except Exception:
        doc.abortTransaction()
        raise
    return len(changed)


def set_panel_tags(doc, objects, tagged=True):
    if not objects:raise ExportError('No parts were selected.')
    return set_panel_tag_choices(doc, [(obj, bool(tagged)) for obj in objects])


def collect_manufacturing_parts(doc, selection, skipped=None):
    candidates, seen_paths = [], set()
    skipped = [] if skipped is None else skipped
    seeds = assembly_seeds(doc, selection)
    explicit = {(object_id(root), path) for root, path, node, normal in seeds
                if not is_container_object(linked_target(node))}

    def walk(root, path, node, labels, ancestors, normal):
        if is_construction_object(node):
            return
        target = linked_target(node)
        if is_construction_object(target):
            return
        semantic_id = object_id(target)
        if semantic_id in ancestors:
            raise ExportError('Circular assembly path: %s.%s' % (root.Label, path))
        if len(ancestors) > 64:
            raise ExportError('Assembly nesting exceeds 64 levels at %s.%s.' % (root.Label, path))
        if is_container_object(target) or node.isDerivedFrom('Assembly::AssemblyLink'):
            # Flexible native subassemblies contain their own component links.
            # Rigid/ordinary links resolve children through the linked container.
            if node.isDerivedFrom('Assembly::AssemblyLink') and not getattr(node, 'Rigid', True):
                children = list(node.Group)
            else:
                children = list(target.ElementList) if target.TypeId == 'App::LinkGroup' else list(getattr(target, 'Group', []))
            referenced = {object_id(linked_target(child)) for child in children
                          if is_link_object(child) and not is_construction_object(child)}
            for child in children:
                # LinkGroup visibility belongs to the instance element, not the source Body.
                # Ordinary assembly links also contain inactive configuration components.
                if target.TypeId == 'App::LinkGroup':
                    if not target.isElementVisible(child.Name):
                        continue
                elif App.GuiUp and not child.ViewObject.Visibility:
                    continue
                # Hidden local link prototypes are definitions, not placements.
                if (not is_link_object(child) and object_id(child) in referenced
                        and App.GuiUp and not child.ViewObject.Visibility):
                    continue
                walk(root, path + child.Name + '.', child, labels + [child.Label],
                     ancestors + (semantic_id,), normal)
            return
        key = (object_id(root), path)
        if key in seen_paths:
            return
        instance = '%s#%s.%s' % (root.Document.Name, root.Name, path)
        if hasattr(target, 'Mesh'):
            skipped.append({'label': ' / '.join(labels), 'source_instance': instance, 'reason': 'Mesh: solid CAD geometry required'})
            return
        if not hasattr(target, 'Shape') and not is_link_object(node):
            return
        try:
            shape = Part.getShape(root, path) if path else Part.getShape(root)
        except Exception as exc:
            raise ExportError('Cannot read assembly instance %s: %s' % (instance, exc)) from exc
        if shape.isNull() or not shape.Solids:
            if target.TypeId == 'PartDesign::Body' or is_link_object(node):
                raise ExportError('Assembly instance %s has no usable solid geometry.' % instance)
            return
        seen_paths.add(key)
        for index, solid in enumerate(shape.Solids, 1):
            label = ' / '.join(labels)
            if len(shape.Solids) > 1:
                label += '_%02d' % index
            # Do not analyse machining or infer material before the user chooses.
            # STEP and native solids are offered on the same terms at every thickness.
            tagged = is_tagged_panel(node, target)
            candidates.append({'shape': solid, 'label': label, 'normal': normal,
                               'tag_object': node, 'component_label': target.Label,
                               'tagged_panel': tagged,
                               'selected_by_default': tagged or (object_id(root), path) in explicit,
                               'selection_root': root,
                               'selection_path': path + ('Solid%d' % index if len(shape.Solids) > 1 else ''),
                               'source_instance': instance + 'Solid%d' % index,
                               'source_document': target.Document.Name, 'source_object': target.Name})


    for root, path, node, normal in seeds:
        labels = [root.Label] if not path else [root.Label, node.Label]
        walk(root, path, node, labels, (), normal)
    if not candidates:
        raise ExportError('No solid CAD parts found. Select an assembly, a subassembly or finished parts. Meshes, sketches and construction geometry cannot be laid flat by this macro.')
    return candidates


def display_part_label(label):
    labels=label.split(' / ')
    return ' / '.join([x for x in labels[:-1] if 'bay ' in x.lower() or 'complete drawer' in x.lower()]+[labels[-1]])


def transfer_fillet_copy(original, prepared, target, label):
    """Transfer only a proven complete rigid copy, never discard later edits."""
    if any(shape.isNull() or not shape.isValid() or len(shape.Solids) != 1
           for shape in (original, prepared, target)):
        raise ExportError('Cannot follow fillet history through %s: a complete single-solid copy is required.' % label)
    tolerance = max(1e-4, target.Volume * 1e-9)
    matches = []
    # Binders may bake the source placement into their geometry or retain it
    # as a TopoShape location. Prove either representation against the target.
    for transform in (App.Placement(), target.Placement.multiply(original.Placement.inverse())):
        expected = original.copy()
        expected.Placement = transform.multiply(expected.Placement)
        if expected.cut(target).Volume + target.cut(expected).Volume <= tolerance:
            result = prepared.copy()
            result.Placement = transform.multiply(result.Placement)
            matches.append(result)
    if not matches:
        raise ExportError('Cannot follow fillet history through %s: the copy has additional geometry changes. '
                          'Set the cutoff to 0 to keep its geometry.' % label)
    if len(matches) > 1 and matches[0].cut(matches[1]).Volume + matches[1].cut(matches[0]).Volume > tolerance:
        raise ExportError('The placement of inherited fillets is ambiguous in ' + label)
    return matches[0]


def inherited_fillet_copy(obj, maximum_radius, ancestors, cache):
    """Resolve whole-shape references/mirrors without changing any document."""
    upstream = None
    if obj.TypeId == 'PartDesign::SubShapeBinder':
        support = list(obj.Support)
        if len(support) == 1 and not any(support[0][1]):
            upstream = linked_target(support[0][0])
    elif obj.TypeId == 'Part::Mirroring':
        upstream = obj.Source
    elif (obj.TypeId == 'PartDesign::Body' and obj.Tip is not None
          and obj.Tip.TypeId == 'PartDesign::FeatureBase'):
        upstream = obj.BaseFeature
    if upstream is None:
        return None
    prepared, report = remove_small_fillets(upstream, maximum_radius, ancestors, cache)
    if report['status'] != 'removed':
        return obj.Shape.copy(), report
    original = upstream.Shape.copy()
    if obj.TypeId == 'Part::Mirroring':
        # Shape.mirror returns a new shape; it does not mutate its input.
        original = original.mirror(obj.Base, obj.Normal)
        prepared = prepared.mirror(obj.Base, obj.Normal)
    result = transfer_fillet_copy(original, prepared, obj.Shape, obj.Label)
    report = dict(report, inherited_via=list(report.get('inherited_via', [])) +
                  [{'document': obj.Document.Name, 'object': obj.Name, 'type': obj.TypeId}])
    return result, report


def remove_small_fillets(body, maximum_radius, ancestors=(), cache=None):
    """Share preparation across linked/mirrored sources within one operation."""
    maximum_radius = float(maximum_radius)
    if not math.isfinite(maximum_radius) or maximum_radius < 0:
        raise ExportError('The fillet cutoff must be a finite, non-negative radius.')
    identity = object_id(body)
    if maximum_radius and (identity in ancestors or len(ancestors) >= 64):
        raise ExportError('Circular or excessively nested fillet source history in ' + body.Label)
    cache = {} if cache is None else cache
    key = (identity, maximum_radius)
    if key not in cache:
        cache[key] = _prepare_fillets(body, maximum_radius, ancestors, cache)
    return cache[key]


def _prepare_fillets(body, maximum_radius, ancestors, cache):
    """Defeature a copy using native fillet history, never arc size alone."""
    original = body.Shape.copy()
    report = {'maximum_radius_mm': maximum_radius, 'inclusive': True,
              'removed_features': [], 'removed_faces': 0, 'added_volume_mm3': 0.0}
    if maximum_radius == 0:
        report['status'] = 'disabled'
        return original, report
    identity = object_id(body)
    inherited = inherited_fillet_copy(body, maximum_radius, ancestors + (identity,), cache)
    if inherited is not None:
        return inherited
    if body.TypeId != 'PartDesign::Body':
        report['status'] = 'no_native_fillet_history'
        return original, report
    features, seen = [], set()
    feature = body.Tip
    while feature is not None:
        if object_id(feature) in seen:
            raise ExportError('Circular feature history in ' + body.Label)
        seen.add(object_id(feature))
        if (feature.TypeId == 'PartDesign::Fillet' and not getattr(feature, 'Suppressed', False)
                and 0 < float(feature.Radius) <= maximum_radius + 1e-9):
            features.append(feature)
        feature = getattr(feature, 'BaseFeature', None)
    if not features:
        report['status'] = 'no_qualifying_fillets'
        return original, report
    if len(original.Solids) != 1 or not original.isValid():
        raise ExportError('Fillet removal requires a valid, single-solid Body. Set the cutoff to 0 to keep its fillets.')

    generated, envelopes = [], []
    for feature in features:
        base = feature.Base[0]
        if base is None:
            raise ExportError('Cannot read the base of fillet ' + feature.Label)
        before, after = base.Shape.copy(), feature.Shape.copy()
        # Body geometry includes its placement; its feature history is local.
        for shape in (before, after):
            shape.Placement = body.Placement.multiply(shape.Placement)
        boundary = Part.makeCompound(before.Faces)
        new_faces = []
        for face in after.Faces:
            if isinstance(face.Surface, Part.Plane):
                continue
            tolerance = max(TOL, face.Area * 1e-8)
            shared = face.common(boundary).Area
            if shared < tolerance:
                new_faces.append(face)
            elif face.Area - shared > tolerance:
                raise ExportError('Cannot isolate the faces created by fillet %s. Set the cutoff to 0 to keep it.' % feature.Label)
        if not new_faces:
            raise ExportError('No removable faces could be identified for fillet ' + feature.Label)
        generated.extend(new_faces)
        envelopes.append(before.cut(after))

    fillet_boundary = Part.makeCompound(generated)
    selected, retained = [], []
    for face in original.Faces:
        if isinstance(face.Surface, Part.Plane):
            retained.append(face)
            continue
        tolerance = max(TOL, face.Area * 1e-8)
        shared = face.common(fillet_boundary).Area
        if shared < tolerance:
            retained.append(face)
        elif abs(face.Area - shared) <= tolerance:
            selected.append(face)
        else:
            raise ExportError('A later feature overlaps a fillet ambiguously. Set the cutoff to 0 or adjust the source fillet.')
    if not selected:
        report['status'] = 'qualifying_fillets_no_longer_exposed'
        return original, report
    try:
        result = original.defeaturing(selected)
        if result.isNull() or not result.isValid() or len(result.Solids) != 1:
            raise ExportError('Removing the selected fillets did not produce one valid solid.')
        volume_tolerance = max(1e-4, original.Volume * 1e-9)
        added = result.cut(original)
        allowed = envelopes[0].multiFuse(envelopes[1:]) if len(envelopes) > 1 else envelopes[0]
        if original.cut(result).Volume > volume_tolerance or added.cut(allowed).Volume > volume_tolerance:
            raise ExportError('Fillet removal changed material outside the selected fillets.')
        boundary = Part.makeCompound(result.Faces)
        for face in retained:
            if abs(face.Area - face.common(boundary).Area) > max(TOL, face.Area * 1e-8):
                raise ExportError('Fillet removal changed another face, hole or pocket.')
        if any(face.common(boundary).Area > max(TOL, face.Area * 1e-8) for face in selected):
            raise ExportError('FreeCAD could not remove all the selected fillet faces.')
        report.update(status='removed', removed_faces=len(selected), added_volume_mm3=added.Volume,
                      removed_features=[{'name': f.Name, 'radius_mm': float(f.Radius),
                                         'document': body.Document.Name, 'body': body.Name} for f in features],
                      validation='No source material removed; added material confined to selected fillets; all other source faces preserved.')
        return result, report
    except Exception as exc:
        raise ExportError('Could not safely remove fillets up to %s mm: %s Set the cutoff to 0 to keep the original geometry.'
                          % (mm(maximum_radius), exc)) from exc


def prepare_candidate(candidate, maximum_radius=0, cache=None):
    """Keep each assembly instance's placement while sharing source processing."""
    source = App.getDocument(candidate['source_document']).getObject(candidate['source_object'])
    prepared, report = remove_small_fillets(source, maximum_radius, cache=cache)
    if report['status'] != 'removed':
        return candidate['shape'], dict(report)
    original = source.Shape.Solids[0]
    placed = candidate['shape']
    if not original.isPartner(placed):
        raise ExportError('Cannot transfer fillet removal to this assembly instance. Scaled or altered links require a separate manufacturing Body.')
    transform = placed.Placement.multiply(original.Placement.inverse())
    result = prepared.copy()
    result.Placement = transform.multiply(result.Placement)
    return result, dict(report)


def build_part_picker(candidates, skipped, QtWidgets, QtCore, parent):
    dialog = QtWidgets.QDialog(parent)
    dialog.setWindowTitle('Choose parts to lay flat')
    dialog.resize(1050, 650)
    layout = QtWidgets.QVBoxLayout(dialog)
    intro = QtWidgets.QLabel('Choose exactly which parts to lay flat. Panel tags and individually selected parts start checked. '
                             'Names, STEP origin and thickness do not exclude solid parts.')
    intro.setWordWrap(True);layout.addWidget(intro)
    search = QtWidgets.QLineEdit();search.setPlaceholderText('Find a part…');layout.addWidget(search)
    table = QtWidgets.QTableWidget(len(candidates), 3)
    table.setObjectName('FreeCADLayFlatPlywoodPartPicker')
    table.setHorizontalHeaderLabels(['Part: checked = include', 'Panel tag', 'Current 3D size (mm)'])
    table.horizontalHeader().setSectionResizeMode(0, QtWidgets.QHeaderView.Stretch)
    for col in [1, 2]:table.horizontalHeader().setSectionResizeMode(col, QtWidgets.QHeaderView.ResizeToContents)
    table.verticalHeader().setVisible(False)
    table.setSelectionBehavior(QtWidgets.QAbstractItemView.SelectRows)
    table.setEditTriggers(QtWidgets.QAbstractItemView.NoEditTriggers)
    for row, candidate in enumerate(candidates):
        item = QtWidgets.QTableWidgetItem(display_part_label(candidate['label']))
        item.setToolTip(candidate['label'])
        item.setFlags(item.flags() | QtCore.Qt.ItemIsUserCheckable)
        item.setCheckState(QtCore.Qt.Checked if candidate['selected_by_default'] else QtCore.Qt.Unchecked)
        table.setItem(row, 0, item)
        table.setItem(row, 1, QtWidgets.QTableWidgetItem('Panel' if candidate['tagged_panel'] else 'Not tagged'))
        box = candidate['shape'].BoundBox
        size = QtWidgets.QTableWidgetItem(' × '.join(mm(value) for value in [box.XLength, box.YLength, box.ZLength]))
        size.setToolTip('Bounding dimensions in the current model orientation. Actual panel thickness is measured after selection.')
        table.setItem(row, 2, size)
    layout.addWidget(table, 1)
    controls = QtWidgets.QHBoxLayout()
    tagged_button = QtWidgets.QPushButton('Select tagged panels')
    shown_button = QtWidgets.QPushButton('Select shown')
    clear_button = QtWidgets.QPushButton('Clear all')
    for button in [tagged_button, shown_button, clear_button]:controls.addWidget(button)
    controls.addStretch();count = QtWidgets.QLabel();controls.addWidget(count);layout.addLayout(controls)
    def selected():
        return [candidate for row, candidate in enumerate(candidates)
                if table.item(row, 0).checkState() == QtCore.Qt.Checked]
    def update_count(*args):
        total = len(selected())
        hidden = sum(table.isRowHidden(row) and table.item(row, 0).checkState() == QtCore.Qt.Checked
                     for row in range(table.rowCount()))
        count.setText('%d of %d selected%s' % (total, len(candidates), ' (%d hidden by search)' % hidden if hidden else ''))
    def set_checks(mode):
        table.blockSignals(True)
        try:
            for row, candidate in enumerate(candidates):
                if mode == 'shown' and table.isRowHidden(row):continue
                checked = mode == 'shown' or (mode == 'tagged' and candidate['tagged_panel'])
                table.item(row, 0).setCheckState(QtCore.Qt.Checked if checked else QtCore.Qt.Unchecked)
        finally:table.blockSignals(False)
        update_count()
    tagged_button.clicked.connect(lambda:set_checks('tagged'))
    shown_button.clicked.connect(lambda:set_checks('shown'))
    clear_button.clicked.connect(lambda:set_checks('clear'))
    def filter_rows(text):
        for row, candidate in enumerate(candidates):table.setRowHidden(row, text.casefold() not in candidate['label'].casefold())
        update_count()
    search.textChanged.connect(filter_rows);table.itemChanged.connect(update_count)
    def highlight():
        try:
            import FreeCADGui as Gui
            Gui.Selection.clearSelection()
            for index in table.selectionModel().selectedRows():
                candidate = candidates[index.row()];root = candidate['selection_root']
                Gui.Selection.addSelection(root.Document.Name, root.Name, candidate['selection_path'])
        except Exception as error:
            App.Console.PrintWarning('Could not highlight part: %s\n' % error)
    table.itemSelectionChanged.connect(highlight)
    if skipped:
        note = QtWidgets.QLabel('%d non-solid items could not be listed. Hover here for details.' % len(skipped))
        note.setToolTip('\n'.join('%s: %s' % (item['label'], item['reason']) for item in skipped))
        note.setWordWrap(True);layout.addWidget(note)
    fillet_row = QtWidgets.QHBoxLayout()
    fillet_row.addWidget(QtWidgets.QLabel('Remove fillets up to'))
    fillet_radius = QtWidgets.QDoubleSpinBox()
    fillet_radius.setObjectName('FreeCADLayFlatFilletRadius')
    fillet_radius.setDecimals(3);fillet_radius.setRange(0, 1000);fillet_radius.setSingleStep(0.1)
    fillet_radius.setSuffix(' mm');fillet_radius.setSpecialValueText('Off — keep all fillets')
    fillet_radius.setValue(1.0)
    fillet_radius.setToolTip('Includes the selected radius. 0 keeps all fillets. Only native PartDesign fillet features are removed; holes and other small curves are preserved.')
    fillet_row.addWidget(fillet_radius);fillet_row.addStretch();layout.addLayout(fillet_row)
    fillet_note = QtWidgets.QLabel('Applies to export copies only, including DXF and 3D files. STEP/imported solids without native fillet history keep their fillets.')
    fillet_note.setWordWrap(True);layout.addWidget(fillet_note)
    note = QtWidgets.QLabel('Next: selected parts are checked, thicknesses are measured, and sheet settings are shown. '
                            'This selection does not change saved panel tags.')
    note.setWordWrap(True);layout.addWidget(note)
    buttons = QtWidgets.QDialogButtonBox(QtWidgets.QDialogButtonBox.Ok | QtWidgets.QDialogButtonBox.Cancel)
    buttons.button(QtWidgets.QDialogButtonBox.Ok).setText('Continue')
    def accept_selection():
        if not selected():
            QtWidgets.QMessageBox.information(dialog, 'Choose a part', 'Select at least one part to lay flat.');return
        dialog.accept()
    buttons.accepted.connect(accept_selection);buttons.rejected.connect(dialog.reject)
    layout.addWidget(buttons);update_count()
    dialog.part_table = table
    dialog.part_search = search
    dialog.selected_candidates = selected
    dialog.select_tagged_button = tagged_button
    dialog.select_shown_button = shown_button
    dialog.clear_button = clear_button
    dialog.fillet_radius = fillet_radius
    return dialog


def choose_plywood_parts(candidates, skipped, QtWidgets, QtCore, parent):
    dialog = build_part_picker(candidates, skipped, QtWidgets, QtCore, parent)
    if dialog.exec() != QtWidgets.QDialog.Accepted:return None
    return [dict(candidate, fillet_radius_mm=dialog.fillet_radius.value()) for candidate in dialog.selected_candidates()]


def save_flat_solids(sheets, path):
    """Standalone exact solids, grouped by sheet, with no external dependencies."""
    previous=App.ActiveDocument;doc=App.newDocument('FreeCADLayFlatFlatPlywood')
    try:
        doc.Label='FreeCAD Lay Flat for CNC — flat panels'
        marker=doc.addObject('App::FeaturePython','FreeCADLayFlatSheetExportMarker');marker.Label='Export copy — source model unchanged'
        offset_y=0.0
        for sheet in sheets:
            group=doc.addObject('App::DocumentObjectGroup','StockSheet')
            group.Label='Sheet %02d — %s mm plywood'%(sheet['index'],mm(sheet['thickness_mm']))
            for placement in sheet['placements']:
                part=placement['part'];obj=doc.addObject('Part::Feature','FlatPlywoodPart')
                obj.Label='%02d %s'%(placement['part_index'],part['label'])
                exact=part['shape'].copy();exact.translate(App.Vector(placement['x_mm'],placement['y_mm']+offset_y,0))
                if not exact.isValid():raise ExportError('Invalid flat copy: '+part['label'])
                obj.Shape=exact;group.addObject(obj)
                obj.addProperty('App::PropertyString','SourceInstance','Source').SourceInstance=part.get('source_instance','')
                obj.addProperty('App::PropertyLength','StockThickness','Manufacturing').StockThickness=part['thickness_mm']
                obj.addProperty('App::PropertyString','CutNotes','Manufacturing').CutNotes='\n'.join(part['notes'])
                if App.GuiUp:
                    obj.ViewObject.ShapeColor=(0.29,0.60,0.68) if abs(part['thickness_mm']-6)<STOCK_THICKNESS_TOL else (0.81,0.73,0.57)
                    obj.ViewObject.DisplayMode='Flat Lines'
            offset_y+=sheet['height_mm']+150
        doc.recompute()
        if App.GuiUp:
            import FreeCADGui as Gui
            Gui.activeDocument().activeView().viewTop();Gui.activeDocument().activeView().fitAll()
        doc.saveAs(str(path))
    finally:
        App.closeDocument(doc.Name)
        if previous is not None:App.setActiveDocument(previous.Name)


def cut_annotations(part, side):
    return ['%s deg taper: wide at %s mm, narrow at %s mm'%(mm(o['angle_deg']),mm(o['start_depth_mm']),mm(o['end_depth_mm']))
            for o in part['operations'] if o['kind']=='TAPER' and o['contour']=='wide' and o['side']==side]


def configure_parts(parts, QtWidgets, QtCore, QtGui, parent):
    parts = [select_machining_face(p) for p in parts]
    dialog = QtWidgets.QDialog(parent)
    dialog.setWindowTitle('FreeCAD Lay Flat for CNC %s — grain, rebates and sheets' % VERSION)
    screen = parent.screen()
    available = screen.availableGeometry() if screen is not None else None
    dialog.resize(min(1120, int(available.width() * 0.9)) if available else 1120,
                  min(900, int(available.height() * 0.85)) if available else 820)
    outer_layout = QtWidgets.QVBoxLayout(dialog)
    intro = QtWidgets.QLabel('The face with most recesses is placed UP; through-openings are cut from that same side. Use Flip over to change a part. One layout is exported per sheet.\nSet each panel’s total quantity and rotation, then preview the sheets. Each assembly instance is counted once before quantities are applied.\nA separate sheet section is provided for each detected thickness. Grain is supplied by you.')
    intro.setWordWrap(True)
    outer_layout.addWidget(intro)
    fillet_reports = [p['fillet_removal'] for p in parts if 'fillet_removal' in p]
    if fillet_reports:
        removed = sum(r['status'] == 'removed' for r in fillet_reports)
        unavailable = sum(r['status'] == 'no_native_fillet_history' for r in fillet_reports)
        cutoffs = ', '.join(mm(v) for v in sorted({r['maximum_radius_mm'] for r in fillet_reports}))
        note = QtWidgets.QLabel('Fillet cutoff: %s mm (inclusive; 0 = off). Removed from %d part(s). '
                                '%d part(s) have no native fillet history and keep their curves. Cancel and return to part selection to change the cutoff.'
                                % (cutoffs, removed, unavailable))
        note.setWordWrap(True);outer_layout.addWidget(note)
    underside=[p for p in parts if p['underside_feature_count']]
    if underside:
        note=QtWidgets.QLabel('%d selected part(s) also have underside machining. It is listed in the part notes and manifest, and retained in 3D; the UP DXFs cover the upper face only.'%len(underside))
        note.setWordWrap(True);outer_layout.addWidget(note)
    note = QtWidgets.QLabel('Create a sheet layout first. Then right-click Sheet layouts or an individual sheet to export DXF, SVG, or both. No files are exported until you choose Export.')
    note.setWordWrap(True);outer_layout.addWidget(note)
    status = QtWidgets.QLabel('Adjust the panels below, then create the sheet layout.')
    status.setWordWrap(True)
    status.setTextInteractionFlags(QtCore.Qt.TextSelectableByMouse)
    outer_layout.addWidget(status)
    scroll = QtWidgets.QScrollArea(dialog)
    scroll.setWidgetResizable(True)
    scroll.setObjectName('FreeCADLayFlatExportScroll')
    scroll.setStyleSheet('QScrollArea#FreeCADLayFlatExportScroll { background-color: #f5f5f5; border: 1px solid #d0d0d0; }')
    content = QtWidgets.QWidget()
    content.setObjectName('FreeCADLayFlatExportContent')
    content.setAutoFillBackground(True)
    content_palette = content.palette()
    content_palette.setColor(QtGui.QPalette.Window, QtGui.QColor('#f5f5f5'))
    content_palette.setColor(QtGui.QPalette.WindowText, QtGui.QColor('#202020'))
    content.setPalette(content_palette)
    # Scope colours to this macro's scroll content, not FreeCAD's global theme.
    # Tables/inputs keep their native control styling and layer swatches.
    content.setStyleSheet('''
        QWidget#FreeCADLayFlatExportContent { background-color: #f5f5f5; color: #202020; }
        QLabel { background-color: transparent; color: #202020; }
        QGroupBox { color: #202020; background-color: #f5f5f5; }
        QCheckBox { color: #202020; }
    ''')
    layout = QtWidgets.QVBoxLayout(content)
    scroll.setWidget(content)
    outer_layout.addWidget(scroll, 1)

    table = QtWidgets.QTableWidget(len(parts), 7)
    table.setHorizontalHeaderLabels(['Part — checked = include', 'Size before rotation (mm)', 'Quantity', 'Rotation', 'Grain before rotation', 'Extend rebates', 'Flip over'])
    table.verticalHeader().setVisible(False)
    table.horizontalHeader().setSectionResizeMode(0, QtWidgets.QHeaderView.Stretch)
    for column in range(1, 7):
        table.horizontalHeader().setSectionResizeMode(column, QtWidgets.QHeaderView.ResizeToContents)
    rotations, grains, extend_boxes, quantities, face_flips = [], [], [], [], []
    for row, part in enumerate(parts):
        item = QtWidgets.QTableWidgetItem('%02d  %s' % (row + 1, display_part_label(part['label'])))
        item.setFlags((item.flags() | QtCore.Qt.ItemIsUserCheckable) & ~QtCore.Qt.ItemIsEditable)
        item.setCheckState(QtCore.Qt.Checked)
        table.setItem(row, 0, item)
        size = QtWidgets.QTableWidgetItem('%s × %s × %s' % (mm(part['width_mm']), mm(part['height_mm']), mm(part['thickness_mm'])))
        size.setFlags(size.flags() & ~QtCore.Qt.ItemIsEditable)
        table.setItem(row, 1, size)
        quantity = QtWidgets.QSpinBox()
        quantity.setRange(0, 999)
        quantity.setValue(1)
        quantity.setKeyboardTracking(False)
        quantity.setToolTip('Total copies to cut for this row, including the existing component. 0 excludes this row. Other assembly instances have their own rows.')
        table.setCellWidget(row, 2, quantity)
        quantities.append(quantity)
        item.setToolTip(part.get('source_instance', part['label']))
        angle = QtWidgets.QComboBox()
        for degrees in (0, 90, 180, 270):
            angle.addItem('%d°' % degrees, degrees)
        angle.setToolTip('Counter-clockwise rotation in the flat view. The sheet packer will not change it.')
        table.setCellWidget(row, 3, angle)
        rotations.append(angle)
        grain = QtWidgets.QComboBox()
        grain.addItem('Unspecified — keep rotation', 'NONE')
        grain.addItem('Along first dimension (X)', 'X')
        grain.addItem('Along second dimension (Y)', 'Y')
        grain.setToolTip('These dimensions refer to the unrotated size shown in this row. After rotation, specified grain must align with the sheet grain.')
        table.setCellWidget(row, 4, grain)
        grains.append(grain)
        extend = QtWidgets.QCheckBox('Use thickness setting')
        extend.setChecked(True)
        extend.setToolTip('Apply the rebate extension from this part’s thickness section. At 0 mm, nothing is extended.')
        table.setCellWidget(row, 5, extend)
        extend_boxes.append(extend)
        flip=QtWidgets.QCheckBox('Flip')
        flip.setObjectName('FreeCADLayFlatFlipPart%d'%row)
        flip.setToolTip('Turn this part over from the automatic most-recessed-face-up orientation. Rotation in the flat view is unchanged.')
        table.setCellWidget(row,6,flip);face_flips.append(flip)
    table.setMinimumHeight(170)
    table.setMaximumHeight(290)
    layout.addWidget(table)
    stock_controls = {}
    detected_thicknesses = sorted({thickness_key(p['thickness_mm']) for p in parts}, key=float)
    for key in detected_thicknesses:
        group = QtWidgets.QGroupBox('%s mm sheet — size and machining clearances' % key)
        grid = QtWidgets.QGridLayout(group)
        controls = {}
        fields = [('width_mm', 'Sheet length X', 2440.0, 1.0),
                  ('height_mm', 'Sheet width Y', 1220.0, 1.0),
                  ('margin_mm', 'Sheet edge margin', 10.0, 0.0),
                  ('gap_mm', 'Gap between machining outlines', 10.0, 0.0),
                  ('extension_mm', 'Extend open rebates past edges', 0.0, 0.0)]
        for i, (field, label, default, minimum) in enumerate(fields):
            box = QtWidgets.QDoubleSpinBox()
            box.setRange(minimum, 100000 if field in ('width_mm', 'height_mm') else 1000)
            box.setDecimals(2)
            box.setKeyboardTracking(False)
            box.setSuffix(' mm')
            box.setValue(default)
            controls[field] = box
            row, col = i // 3, (i % 3) * 2
            grid.addWidget(QtWidgets.QLabel(label), row, col)
            grid.addWidget(box, row, col + 1)
        controls['extension_mm'].setToolTip('0 = off. Extension for %s mm panels only; the per-part checkbox can exclude a panel.' % key)
        controls['gap_mm'].setToolTip('Clear space between machining envelopes for this thickness, including rebate extensions. Set for your tooling.')
        sheet_grain = QtWidgets.QComboBox()
        sheet_grain.addItem('Along length X', 'X')
        sheet_grain.addItem('Along width Y', 'Y')
        grid.addWidget(QtWidgets.QLabel('Sheet grain'), 1, 4)
        grid.addWidget(sheet_grain, 1, 5)
        stock_controls[key] = {'values': controls, 'grain': sheet_grain}
        layout.addWidget(group)
    legend = QtWidgets.QLabel('Click a colour button or double-click a layer name below the preview to edit it. Matching holes share one layer; depths stay unchanged.\nNominal 8 × 4 ft default: 2440 × 1220 mm. Different thicknesses use separate sheets. No automatic rotation or irregular-shape nesting.')
    legend.setWordWrap(True)
    layout.addWidget(legend)
    scene = QtWidgets.QGraphicsScene(dialog)
    view = QtWidgets.QGraphicsView(scene)
    view.setObjectName('FreeCADLayFlatSheetGraphicsPreview')
    view.setMinimumHeight(260)
    view.setRenderHint(QtGui.QPainter.Antialiasing)
    view.setBackgroundBrush(QtGui.QBrush(QtGui.QColor('white')))
    layout.addWidget(view, 1)
    colour_key = QtWidgets.QTableWidget(0, 3)
    colour_key.setHorizontalHeaderLabels(['Colour', 'Layer name — double-click to edit', 'Features'])
    colour_key.verticalHeader().setVisible(False)
    colour_key.horizontalHeader().setSectionResizeMode(0, QtWidgets.QHeaderView.ResizeToContents)
    colour_key.horizontalHeader().setSectionResizeMode(1, QtWidgets.QHeaderView.Stretch)
    colour_key.horizontalHeader().setSectionResizeMode(2, QtWidgets.QHeaderView.ResizeToContents)
    colour_key.setEditTriggers(QtWidgets.QAbstractItemView.DoubleClicked | QtWidgets.QAbstractItemView.EditKeyPressed)
    colour_key.setMaximumHeight(145)
    layout.addWidget(colour_key)
    button_row = QtWidgets.QHBoxLayout()
    update = QtWidgets.QPushButton('Update sheet preview')
    button_row.addWidget(update)
    auto_preview = QtWidgets.QCheckBox('Automatically update preview')
    auto_preview.setChecked(True)
    auto_preview.setToolTip('Preview draws when the window opens and refreshes after a 0.5-second pause when parts, flip, rotation, quantities or sheet settings change.')
    button_row.addWidget(auto_preview)
    button_row.addStretch()
    buttons = QtWidgets.QDialogButtonBox(QtWidgets.QDialogButtonBox.Ok | QtWidgets.QDialogButtonBox.Cancel)
    buttons.button(QtWidgets.QDialogButtonBox.Ok).setText('Create sheet layout')
    buttons.rejected.connect(dialog.reject)
    button_row.addWidget(buttons)
    outer_layout.addLayout(button_row)
    chosen_result = {}
    orientation_sources=[p.get('_unoriented_part',p) for p in parts]
    initial_palette = palette_for_parts(orientation_sources)
    sources = {op['layer'] for part in orientation_sources for op in part['operations']}
    layer_settings = {key: {'name': key, 'hex': value['hex']} for key, value in initial_palette.items() if key in sources}
    preview_state = {'busy': False, 'dirty': True, 'cached': None, 'picking_colour': False}
    auto_timer = QtCore.QTimer(dialog)
    auto_timer.setSingleShot(True)
    style_timer = QtCore.QTimer(dialog)
    style_timer.setSingleShot(True)

    def build():
        cached = preview_state['cached']
        if cached is not None and not preview_state['dirty']:
            configured, settings, sheets = cached
            configured, sheets = apply_layout_styles(configured, sheets, layer_settings)
            return configured, settings, sheets
        settings = {'by_thickness': {}}
        configured = []
        for row, part in enumerate(parts):
            quantity = quantities[row].value()
            if table.item(row, 0).checkState() != QtCore.Qt.Checked or quantity == 0:
                continue
            if len(configured) + quantity > 5000:
                raise ExportError('This batch exceeds 5,000 panels. Split it into smaller exports.')
            key = thickness_key(part['thickness_mm'])
            if key not in settings['by_thickness']:
                widgets = stock_controls[key]
                values = {name: control.value() for name, control in widgets['values'].items()}
                values['grain_axis'] = widgets['grain'].currentData()
                try:
                    settings['by_thickness'][key] = sheet_settings(values)
                except Exception as exc:
                    raise ExportError('%s mm sheet settings: %s' % (key, exc)) from exc
            profile = settings['by_thickness'][key]
            amount = profile['extension_mm'] if extend_boxes[row].isChecked() else 0
            try:
                configured_part = apply_part_options(part, rotations[row].currentData(), grains[row].currentData(), amount, face_flips[row].isChecked())
                configured.extend(expand_quantity(configured_part, quantity, row + 1))
            except Exception as exc:
                raise ExportError('%s: %s' % (part['label'], exc)) from exc
        configured = apply_layer_settings(configured, layer_settings)
        return configured, settings, pack_sheets(configured, settings)


    def pen(colour, width=1.2):
        value = QtGui.QPen(QtGui.QColor(colour))
        value.setWidthF(width)
        value.setCosmetic(True)
        return value

    def render(sheets, settings):
        scene.clear()
        palette = palette_for_parts([p['part'] for sheet in sheets for p in sheet['placements']])
        refresh_layer_key([p['part'] for sheet in sheets for p in sheet['placements']])
        top = 0.0
        for sheet in sheets:
            sheet_profile = sheet['stock_settings']
            width, height = sheet['width_mm'], sheet['height_mm']
            for side in ['FRONT'] + (['BACK'] if sheet['has_back'] else []):
                scene.addRect(0, top, width, height, pen(palette['REFERENCE_SHEET']['hex']))
                margin = sheet_profile['margin_mm']
                if margin:
                    scene.addRect(margin, top + margin, width - 2 * margin, height - 2 * margin, pen(palette['REFERENCE_MARGIN']['hex'], 0.8))
                title = scene.addSimpleText('Sheet %02d · %s · %s mm · grain %s' % (sheet['index'], face_label(side), mm(sheet['thickness_mm']), sheet_profile['grain_axis']))
                title.setScale(max(width, height) / 1200)
                title.setPos(0, top - max(width, height) / 35)
                for placement in sheet['placements']:
                    part = placement['part']
                    for op in face_operations(part, side):
                        colour = palette[op['layer']]['hex']
                        for source_wire in op['face'].Wires:
                            wire = placed_wire(source_wire, placement, sheet, side)
                            for edge in wire.Edges:
                                if edge.Length <= TOL:
                                    continue
                                path = QtGui.QPainterPath()
                                count = 1 if isinstance(edge.Curve, Part.Line) else 96
                                for i in range(count + 1):
                                    p = edge.valueAt(edge.FirstParameter + (edge.LastParameter - edge.FirstParameter) * i / count)
                                    point = QtCore.QPointF(p.x, top + height - p.y)
                                    if i == 0:
                                        path.moveTo(point)
                                    else:
                                        path.lineTo(point)
                                scene.addPath(path, pen(colour))
                    x = placement['x_mm'] if side == 'FRONT' else width - placement['x_mm'] - part['width_mm']
                    y = placement['y_mm']
                    for a, b in grain_segments(x, y, part['width_mm'], part['height_mm'], part['grain_axis_on_sheet']):
                        scene.addLine(a[0], top + height - a[1], b[0], top + height - b[1], pen(palette['REFERENCE_GRAIN']['hex']))
                    label = scene.addSimpleText('%02d %s (%d°)' % (placement['part_index'], part['label'], part['rotation_deg']))
                    label.setBrush(QtGui.QBrush(QtGui.QColor('#555555')))
                    # Scale the entire label to fit inside even a narrow part.
                    text_width = max(1, label.boundingRect().width())
                    label.setScale(min(1.4, part['width_mm'] * 0.8 / text_width, part['height_mm'] / 35))
                    label.setPos(x + 3, top + height - y - part['height_mm'] + 3)
                top += height + max(width, height) / 10
        scene.setSceneRect(scene.itemsBoundingRect().adjusted(-20, -20, 20, 20))
        view.fitInView(scene.sceneRect(), QtCore.Qt.KeepAspectRatio)

    def refresh_layer_key(configured):
        counts = {}
        for part in configured:
            for op in part['operations']:
                source = op.get('source_layer', op['layer'])
                counts[source] = counts.get(source, 0) + 1
        sources = [key for key in layer_settings if key in counts]
        was_blocked = colour_key.blockSignals(True)
        try:
            colour_key.setRowCount(len(sources))
            for row, source in enumerate(sources):
                style = layer_settings[source]
                button = QtWidgets.QPushButton('Choose…')
                colour = QtGui.QColor(style['hex'])
                foreground = '#ffffff' if colour.lightness() < 140 else '#202020'
                button.setStyleSheet('QPushButton { background-color: %s; color: %s; border: 1px solid #999; border-radius: 3px; padding: 3px 8px; }' % (style['hex'], foreground))
                button.setToolTip('Change colour for %s' % style['name'])
                button.clicked.connect(lambda _checked=False, key=source: choose_layer_colour(key))
                colour_key.setCellWidget(row, 0, button)
                name = QtWidgets.QTableWidgetItem(style['name'])
                name.setData(QtCore.Qt.UserRole, source)
                name.setToolTip('Original operation: %s\nRenaming changes the layer name, not its depth or diameter.' % source)
                colour_key.setItem(row, 1, name)
                count = QtWidgets.QTableWidgetItem(str(counts[source]))
                count.setFlags(count.flags() & ~QtCore.Qt.ItemIsEditable)
                colour_key.setItem(row, 2, count)
        finally:
            colour_key.blockSignals(was_blocked)

    def refresh_styles():
        focused = QtWidgets.QApplication.focusWidget()
        editing_name = isinstance(focused, QtWidgets.QLineEdit) and colour_key.isAncestorOf(focused)
        if preview_state['busy'] or preview_state['picking_colour'] or editing_name:
            style_timer.start(150)
            return
        try:
            cached = preview_state['cached']
            if cached is not None and not preview_state['dirty']:
                configured, settings, sheets = cached
                configured, sheets = apply_layout_styles(configured, sheets, layer_settings)
                render(sheets, settings)
                preview_state['cached'] = (configured, settings, sheets)
                status.setText('Layer names and colours updated. The export will use these settings.')
            else:
                refresh_layer_key(apply_layer_settings(parts, layer_settings))
                if auto_preview.isChecked():
                    auto_timer.start(500)
                else:
                    status.setText('Layer settings updated. Click Update sheet preview to refresh the geometry.')
        except Exception as exc:
            status.setText('Layer settings need attention: %s' % exc)
            QtWidgets.QMessageBox.warning(dialog, 'Layer settings need attention', str(exc))

    def choose_layer_colour(source):
        auto_timer.stop()
        style_timer.stop()
        preview_state['picking_colour'] = True
        try:
            selected = QtWidgets.QColorDialog.getColor(QtGui.QColor(layer_settings[source]['hex']), dialog,
                                                       'Colour for ' + layer_settings[source]['name'])
            if selected.isValid():
                layer_settings[source]['hex'] = selected.name().lower()
                style_timer.start(0)
        except Exception as exc:
            QtWidgets.QMessageBox.warning(dialog, 'Could not change layer colour', str(exc))
        finally:
            preview_state['picking_colour'] = False
            if auto_preview.isChecked() and preview_state['dirty']:
                auto_timer.start(500)

    def layer_name_changed(item):
        if item.column() != 1:
            return
        source = item.data(QtCore.Qt.UserRole)
        if source not in layer_settings:
            return
        old_name = layer_settings[source]['name']
        layer_settings[source]['name'] = item.text().strip()
        try:
            validate_layer_settings(layer_settings)
        except Exception as exc:
            layer_settings[source]['name'] = old_name
            was_blocked = colour_key.blockSignals(True)
            try:
                item.setText(old_name)
            finally:
                colour_key.blockSignals(was_blocked)
            QtWidgets.QMessageBox.warning(dialog, 'Layer name needs attention', str(exc))
            return
        # Defer rebuilding table cells until the edit callback has returned.
        style_timer.start(0)


    def update_preview(*args, automatic=False):
        auto_timer.stop()
        if automatic and not auto_preview.isChecked():
            return None
        focused = QtWidgets.QApplication.focusWidget()
        editing_name = isinstance(focused, QtWidgets.QLineEdit) and colour_key.isAncestorOf(focused)
        if preview_state['busy'] or preview_state['picking_colour'] or (automatic and editing_name):
            if automatic and auto_preview.isChecked():
                auto_timer.start(150)
            return None
        style_timer.stop()
        error = None
        preview_state['busy'] = True
        update.setEnabled(False)
        status.setText('Calculating sheet preview…')
        QtWidgets.QApplication.setOverrideCursor(QtCore.Qt.WaitCursor)
        try:
            configured, settings, sheets = build()
            render(sheets, settings)
            preview_state['cached'] = (configured, settings, sheets)
            preview_state['dirty'] = False
            extended = sum(p['extended_open_edges'] for p in configured)
            underside_count=sum(p['underside_feature_count'] for p in configured)
            status.setText('%d parts on %d UP sheet(s). %d open rebate edge(s) extended. All boundaries fit within the margins.%s' % (len(configured), len(sheets), extended, (' %d underside feature(s) remain in 3D and notes only.'%underside_count) if underside_count else ''))
            return configured, settings
        except Exception as exc:
            scene.clear()
            preview_state['dirty'] = True
            status.setText('Layout needs attention: %s' % exc)
            error = str(exc)
            App.Console.PrintError('Lay Flat for CNC sheet preview: %s\n' % exc)
        finally:
            QtWidgets.QApplication.restoreOverrideCursor()
            preview_state['busy'] = False
            update.setEnabled(True)
        # Automatic mode reports errors in the always-visible status area. It
        # does not interrupt every intermediate edit with a modal warning.
        if error is not None and not automatic:
            QtWidgets.QMessageBox.warning(dialog, 'Sheet preview needs attention', error)
        return None

    def invalidate(*args):
        preview_state['dirty'] = True
        if auto_preview.isChecked():
            status.setText('Settings changed — preview will update after a short pause…')
            auto_timer.start(500)
        else:
            auto_timer.stop()
            status.setText('Preview is out of date — click Update sheet preview. Export will check the current settings again.')

    def automatic_changed(enabled):
        auto_timer.stop()
        if enabled:
            status.setText('Automatic preview enabled — calculating shortly…')
            auto_timer.start(500)
        elif preview_state['dirty']:
            status.setText('Automatic preview is off. Click Update sheet preview to show the current settings.')
        else:
            status.setText('Automatic preview is off. The current preview is up to date.')


    def accept_layout():
        auto_timer.stop()
        style_timer.stop()
        error = None
        status.setText('Checking the sheet layout…')
        QtWidgets.QApplication.setOverrideCursor(QtCore.Qt.WaitCursor)
        try:
            # An unchanged cached build has already passed geometry/packing
            # checks. Dirty or absent previews still run the full validation.
            configured, settings, sheets = build()
        except Exception as exc:
            error = str(exc)
            App.Console.PrintError('Lay Flat for CNC export validation: %s\n' % exc)
        finally:
            QtWidgets.QApplication.restoreOverrideCursor()
        if error is not None:
            status.setText('Export stopped: %s' % error)
            QtWidgets.QMessageBox.warning(dialog, 'Export stopped — no files saved', error)
            return
        chosen_result['parts'], chosen_result['settings'] = configured, settings
        chosen_result['sheets'] = sheets
        dialog.accept()

    def create_layout_clicked():
        # Qt invokes slots outside run()'s exception handler. Catch every error
        # here too, otherwise an exception can look like an unresponsive button.
        try:
            accept_layout()
        except Exception as exc:
            status.setText('Export stopped: %s' % exc)
            App.Console.PrintError(traceback.format_exc() + '\n')
            QtWidgets.QMessageBox.critical(dialog, 'Export stopped — no files saved', str(exc))

    update.clicked.connect(update_preview)
    auto_timer.timeout.connect(lambda: update_preview(automatic=True))
    style_timer.timeout.connect(refresh_styles)
    auto_preview.toggled.connect(automatic_changed)
    colour_key.itemChanged.connect(layer_name_changed)
    dialog.finished.connect(lambda *_: auto_timer.stop())
    dialog.finished.connect(lambda *_: style_timer.stop())
    buttons.accepted.connect(create_layout_clicked)
    for combo in rotations + grains + [widgets['grain'] for widgets in stock_controls.values()]:
        combo.currentIndexChanged.connect(invalidate)
    for widgets in stock_controls.values():
        for control in widgets['values'].values():
            control.valueChanged.connect(invalidate)
    for quantity in quantities:
        quantity.valueChanged.connect(invalidate)
    for checkbox in extend_boxes + face_flips:
        checkbox.toggled.connect(invalidate)
    table.itemChanged.connect(invalidate)
    refresh_layer_key(apply_layer_settings(parts, layer_settings))
    # Paint once after the visible dialog has a real viewport, then refresh on edits.
    auto_timer.start(100)
    if dialog.exec() != QtWidgets.QDialog.Accepted:
        return None
    return chosen_result


def run():
    import FreeCADGui as Gui
    try:
        from PySide import QtWidgets, QtCore, QtGui
    except ImportError:
        from PySide2 import QtWidgets, QtCore, QtGui
    parent = Gui.getMainWindow()
    doc = App.ActiveDocument
    if doc is None:
        QtWidgets.QMessageBox.information(parent, 'FreeCAD Lay Flat for CNC', 'Open a FreeCAD model first.')
        return
    try:
        if doc.getObject('FreeCADLayFlatSheetExportMarker') is not None or doc.getObject('MestraSheetExportMarker') is not None:
            root = doc.getObject('SheetLayouts')
            if root is not None and 'ExportPayload' in root.PropertiesList:
                sheet_runtime().export_dialog(root)
                return
            root = sheet_runtime().upgrade_legacy_layout(doc)
            sheet_runtime().export_dialog(root)
            return
        skipped=[]
        candidates = collect_manufacturing_parts(doc, Gui.Selection.getSelectionEx(), skipped)
        candidates = choose_plywood_parts(candidates, skipped, QtWidgets, QtCore, parent)
        if candidates is None:
            return
        parts, failures, fillet_cache = [], [], {}
        parent.statusBar().showMessage('Reading individual panels…')
        QtWidgets.QApplication.setOverrideCursor(QtCore.Qt.WaitCursor)
        try:
            for candidate in candidates:
                try:
                    shape, fillet_report = prepare_candidate(candidate, candidate.get('fillet_radius_mm', 0), fillet_cache)
                except Exception as exc:
                    failures.append('%s: %s' % (candidate['label'], exc))
                    continue
                for index, solid in enumerate(shape.Solids, 1):
                    label = candidate['label']
                    if len(shape.Solids) > 1:
                        label += '_%02d' % index
                    try:
                        part = select_machining_face(analyse_solid(solid, label, candidate['normal']))
                        part['fillet_removal'] = fillet_report
                        if fillet_report['status'] == 'removed':
                            part['notes'].append('Export copy: native fillets up to and including %s mm removed; source model unchanged.' % mm(fillet_report['maximum_radius_mm']))
                        elif fillet_report['status'] == 'no_native_fillet_history':
                            part['notes'].append('Fillet removal not applied: no native PartDesign Body history; original curves retained.')
                        part['source_object'] = candidate['source_object']
                        part['source_document'] = candidate['source_document']
                        part['source_instance'] = candidate['source_instance']
                        parts.append(part)
                    except Exception as exc:
                        failures.append('%s: %s' % (label, exc))
        finally:
            QtWidgets.QApplication.restoreOverrideCursor()
            parent.statusBar().clearMessage()
        if failures:
            raise ExportError('No files were exported. These selected parts need attention. You can run again and untick them in the part picker:\n\n' + '\n\n'.join(failures))
        if not parts:
            raise ExportError('No solid parts were found.')
        choice = configure_parts(parts, QtWidgets, QtCore, QtGui, parent)
        if choice is None:
            return
        QtWidgets.QApplication.setOverrideCursor(QtCore.Qt.WaitCursor)
        parent.statusBar().showMessage('Creating sheet layout…')
        try:
            save_sheet_preview(choice['sheets'], choice['settings'], title=doc.Label)
        finally:
            QtWidgets.QApplication.restoreOverrideCursor()
            parent.statusBar().clearMessage()
        App.Console.PrintMessage('Sheet layout created. Right-click Sheet layouts or a sheet to export DXF/SVG. No files have been exported.\n')
    except ExportError as exc:
        App.Console.PrintError('FreeCAD Lay Flat for CNC: %s\n' % exc)
        QtWidgets.QMessageBox.warning(parent, 'Export needs attention', str(exc))
    except Exception as exc:
        App.Console.PrintError(traceback.format_exc() + '\n')
        QtWidgets.QMessageBox.critical(parent, 'Export failed', 'The export could not be completed. Your source model was not changed.\n\n%s\n\nSee View → Panels → Report View for details.' % exc)


if __name__ == '__main__':
    run()
